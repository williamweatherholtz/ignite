// IgniteDeliveryS14 — Sprint 14: native headless-sync (dPlugins) — Obsidian-Sync compat.
// A Rust server-plugin trait + the headless-sync plugin (obsidian-headless CLI wrapper +
// /api/ext/headless-sync/* routes + the plugin:headless-sync WS channel). Also consumes the
// subscribe-channel tracking from sprint06. PLANNED to standup; implement gate pends the build.
package IgniteDeliveryS14 {
    private import EngineElement::*;
    private import EngineWork::*;
    private import EngineVerification::*;
    private import EngineRelationships::*;

    #CharteredBy dependency from headlessSyncStory to srWireCompat;

    part headlessSyncStory : Story {
        :>> id = "29206cc3-ed6d-4de3-b80b-f039ece9d863";
        :>> title = "Sprint 14: native headless-sync (Rust plugin trait + obsidian-headless CLI + WS channel) (dPlugins, srWireCompat)";
        :>> createdAt = "2026-07-02"; :>> createdBy = "will"; :>> kind = WorkKind::code; :>> priority = WorkPriority::p2; :>> owner = "ai"; :>> estimatedPoints = 8;
    }

    action def DeliveryRunS14 {
        action storyHeadlessSync;
        verification storyHeadlessSyncDoD : Test { :>> id = "28c81dc8-9ef2-4375-af61-f00cb5f4c350"; :>> method = VerificationMethod::test; :>> procedureText = "Native headless-sync per dPlugins, wire-compatible with Ignis c9656b8 (check apps/ignis-server/server/plugins/headless-sync/ - routes.js, sync-manager.js, ob-cli.js, broadcaster.js). (1) A Rust SERVER-PLUGIN trait (register routes + a WS channel + shutdown) - the seam dPlugins called for. (2) The headless-sync plugin implementing it: /api/ext/headless-sync/{status,login,logout,setup,start,stop,unlink,logs,vaults,create-remote-vault,remote-vaults} with the Ignis shapes ({installed,version,authenticated,email,name}; {success,state}; {logs:[]}; {vaults:{}}; etc.); wraps the obsidian-headless CLI via an INJECTED runner trait (so tests use a fake, no real CLI needed); persists token + per-vault sync state as JSON in a plugin data dir (DATA_ROOT/plugins/headless-sync). (3) Broadcast sync-log / sync-status on the plugin:headless-sync WS channel - CONSUMING the subscribe-channel tracking added in sprint06 (wire channel-scoped broadcast into ws.rs). (4) GET /api/plugins now lists headless-sync. VERIFY (tests, fake CLI runner + tempdir data dir): status reflects auth state; login persists + round-trips; setup/start/stop update + return state; logs/vaults shapes; a WS client subscribed to plugin:headless-sync receives a sync-status broadcast; /api/plugins includes headless-sync. clippy -D warnings + cargo test green; keel validate + guard green. HONEST: real obsidian-headless CLI integration is NOT tested (CLI absent) - the runner is faked; note it."; }
        part storyHeadlessSyncDoDR1 : TestResult { :>> id = "2184dc04-b015-4e10-bd02-f14883c6022e"; :>> outcome = VerdictKind::pass; :>> judgedAgainst = "ceca03b"; :>> judgedAt = "2026-07-02"; :>> judgedBy = "ai"; :>> notes = "src/plugins.rs (ServerPlugin trait + ChannelHub) + src/headless_sync.rs (11 /api/ext/headless-sync/* routes, injected CliRunner, token/per-vault state under DATA_ROOT/plugins/headless-sync, plugin:headless-sync WS broadcast). ws.rs now routes channel-scoped broadcasts (consumes sprint06's subscribe-channel tracking). /api/plugins lists headless-sync via injected PluginDescriptors. 82 tests pass (8 new: status/login-persist, logout, setup/start/stop transitions + vaults map, logs/remote-vaults shapes, channel broadcast, plugin-hub), clippy + fmt clean. HONEST GAP: the REAL obsidian-headless CLI path is not integration-tested (CliRunner faked; CLI absent) + some sync-state fields inferred from sync-manager.js."; }
        part storyHeadlessSyncDoDR2 : TestResult { :>> id = "e355a917-3b5a-4881-9b41-00ed456b8280"; :>> outcome = VerdictKind::pass; :>> judgedAgainst = "da685ef"; :>> judgedAt = "2026-07-02"; :>> judgedBy = "claudeOpus"; }
        part storyHeadlessSyncDoDR3 : TestResult { :>> id = "0fd54689-e630-4b6f-ae6c-1aa2ca61d17d"; :>> outcome = VerdictKind::pass; :>> judgedAgainst = "9f29e89"; :>> judgedAt = "2026-07-02"; :>> judgedBy = "claudeOpus"; }
    }

    verification headlessSyncRefineGate : Test { :>> id = "090a9e23-e913-4d5c-bc34-cee3c2e4a701"; :>> title = "Sprint 14 refine gate (DoR)"; :>> createdAt = "2026-07-02"; :>> createdBy = "ai"; :>> method = VerificationMethod::inspect; :>> procedureText = "DoR: native headless-sync (dPlugins) - the last srWireCompat feature. Shapes + behavior from the cloned headless-sync plugin source. Testable via an injected fake CLI runner (real CLI absent). INVEST: Independent (new module + a WS-channel hook); Valuable (Obsidian-Sync compat); Estimable (8pts - plugin trait + ~11 routes + CLI wrapper + WS channel + state); Small-ish (one sprint); Testable (fake runner + tempdir). DoR met."; }
    part headlessSyncRefineGateR1 : TestResult { :>> id = "7d940fd6-3341-45e1-bdfd-2af1a1fb4423"; :>> outcome = VerdictKind::pass; :>> judgedAgainst = "a04e7fd"; :>> judgedAt = "2026-07-02"; :>> judgedBy = "ai"; }
    verification headlessSyncStandupGate : Test { :>> id = "b027a6aa-ce14-4615-8f6a-9feae3bde6fe"; :>> title = "Sprint 14 standup gate"; :>> createdAt = "2026-07-02"; :>> createdBy = "ai"; :>> method = VerificationMethod::inspect; :>> procedureText = "Approach: define a ServerPlugin trait (id/name + routes + optional WS channel + shutdown); implement HeadlessSyncPlugin with an injected CliRunner trait (real = std::process obsidian-headless; test = fake); persist token/state JSON under DATA_ROOT/plugins/headless-sync; extend ws.rs with channel-scoped broadcast (consume the subscribe-channel set) + a broadcaster the plugin uses for sync-log/sync-status; wire the ext routes + /api/plugins listing. TDD with the fake runner + tempdir. No blockers; implement gate pends the build."; }
    part headlessSyncStandupGateR1 : TestResult { :>> id = "6ceacd11-a2d5-4262-99ee-452dcb5e9a34"; :>> outcome = VerdictKind::pass; :>> judgedAgainst = "a04e7fd"; :>> judgedAt = "2026-07-02"; :>> judgedBy = "ai"; }
    verification headlessSyncImplementGate : Test { :>> id = "79e219b9-5927-4427-91e8-9557591a807b"; :>> title = "Sprint 14 implement gate"; :>> createdAt = "2026-07-02"; :>> createdBy = "ai"; :>> method = VerificationMethod::test; :>> procedureText = "Built test-first (8 tests RED first). 82 tests pass: status/login-persist, logout, setup/start/stop + vaults map, logs+remote-vaults shapes, channel-scoped WS broadcast, plugin hub. clippy -D warnings + fmt clean. Verified live at ceca03b. (The fork stopped after backgrounding a compile; a finish-check confirmed 82 green + clippy clean + /api/plugins wiring before closing.)"; }
    part headlessSyncImplementGateR1 : TestResult { :>> id = "9e421416-453d-47c3-a198-341ebfd82393"; :>> outcome = VerdictKind::pass; :>> judgedAgainst = "ceca03b"; :>> judgedAt = "2026-07-02"; :>> judgedBy = "ai"; }
    verification headlessSyncReviewGate : Test { :>> id = "c0345426-ea5d-4c7b-972f-c670e976e748"; :>> title = "Sprint 14 review gate"; :>> createdAt = "2026-07-02"; :>> createdBy = "ai"; :>> method = VerificationMethod::inspect; :>> procedureText = "Reviewed: ServerPlugin trait is a clean minimal seam (dPlugins delivered); routes match routes.js shapes; CliRunner injected (RealCli shells out to obsidian-headless; fake in tests); state persisted under the Ignis-style data dir; the WS ChannelHub finally consumes the subscribe-channel tracking (closes the sprint06 note) without breaking file-event broadcast; /api/plugins lists headless-sync. Honest gap: real CLI path faked (untested). Sound - completes srWireCompat's feature surface."; }
    part headlessSyncReviewGateR1 : TestResult { :>> id = "9a9727e3-38b1-4ef5-b0b6-e992d8c5d240"; :>> outcome = VerdictKind::pass; :>> judgedAgainst = "ceca03b"; :>> judgedAt = "2026-07-02"; :>> judgedBy = "ai"; }
    verification headlessSyncCloseOutGate : Test { :>> id = "ec5f7ca6-56bd-4ff1-bb5c-baf70af6ed0c"; :>> title = "Sprint 14 closeOut gate (autonomous, D0049)"; :>> createdAt = "2026-07-02"; :>> createdBy = "ai"; :>> method = VerificationMethod::inspect; :>> procedureText = "Autonomous closeOut (D0049): DoD pass; native headless-sync + the Rust plugin seam are built. cargo test (82) + clippy + keel validate/guard green. srWireCompat's route + feature surface is now complete in Rust; the remaining major piece is deployment (Docker image, dDeploymentDirection)."; }
    part headlessSyncCloseOutGateR1 : TestResult { :>> id = "8234dcfc-fa52-458d-8860-fc3f2f7a9c08"; :>> outcome = VerdictKind::pass; :>> judgedAgainst = "ceca03b"; :>> judgedAt = "2026-07-02"; :>> judgedBy = "ai"; }
    verification headlessSyncRetroGate : Test { :>> id = "a44d5fa0-a143-4616-a8d0-3364aa577016"; :>> title = "Sprint 14 retro gate (autonomous, D0049)"; :>> createdAt = "2026-07-02"; :>> createdBy = "ai"; :>> method = VerificationMethod::analyze; :>> procedureText = "Autonomous retro (D0049). WELL: dPlugins' native-reimplementation call paid off - a small ServerPlugin trait + an injected CliRunner made a CLI-dependent feature fully unit-testable without the CLI; wiring the ChannelHub closed the sprint06 subscribe-channel loose end for free. AVOIDABLE-ISSUE SCAN: no new tracked issues - the faked-CLI test coverage is an accepted, unavoidable limit (no obsidian-headless in the env); a couple of sync-state fields were inferred. PROCESS NOTE (recurring): a fork again stopped after backgrounding a slow compile without reporting - a finish-check (test+clippy+wiring) before closing is now standard for these. LESSON: inject external-process dependencies behind a trait so the happy path is testable + the real binary is a deploy concern. Estimate 8pt held."; }
    part headlessSyncRetroGateR1 : TestResult { :>> id = "2cd437c2-fe39-4851-97c0-4179123f9670"; :>> outcome = VerdictKind::pass; :>> judgedAgainst = "ceca03b"; :>> judgedAt = "2026-07-02"; :>> judgedBy = "ai"; }
}
