// IgniteDeliveryS08 — Sprint 8: /api/bootstrap cold-start bundle + vault/list + vault/info
// (read-only vault ops), wire-compatible with Ignis c9656b8, under srWireCompat. Served from
// the warm registry/index; no registry mutation (vault create/rename/remove is sprint09).
// PLANNED to standup; implement gate pends the build.
package IgniteDeliveryS08 {
    private import EngineElement::*;
    private import EngineWork::*;
    private import EngineVerification::*;
    private import EngineRelationships::*;

    // chartered by srWireCompat (IgniteRequirements); name-ref, no import.
    #CharteredBy dependency from bootstrapVaultStory to srWireCompat;

    part bootstrapVaultStory : Story {
        :>> id = "bf2a6d8b-f0c8-4b6f-a857-acbafdc2197a";
        :>> title = "Sprint 8: /api/bootstrap + vault/list + vault/info (read-only) - the cold-start bundle (srWireCompat)";
        :>> createdAt = "2026-06-30"; :>> createdBy = "will"; :>> kind = WorkKind::code; :>> priority = WorkPriority::p0; :>> owner = "ai"; :>> estimatedPoints = 5;
    }

    action def DeliveryRunS08 {
        action storyBootstrapVault;
        verification storyBootstrapVaultDoD : Test { :>> id = "0812b40c-1444-4a2d-8c53-54f0f3b3cb0c"; :>> method = VerificationMethod::test; :>> procedureText = "Implement the read-only vault + cold-start routes wire-compatible with Ignis c9656b8: GET /api/vault/list -> [{id,name,path}]; GET /api/vault/info?vault (default first) -> {id,name,path,platform,version}; GET /api/bootstrap?vault (default first) -> {vault:{id,name,path,platform,version}, vaultList:[{id,name,path}], tree:<Ignis fs/tree shape from the warm index>, plugins:[], virtualPlugins:[], settings:{contentCacheBytes,inputCacheBytes,inputCacheTtlMs,directFetchHosts}}. Derive vault id the same way Ignis does (check the cloned vault.js). platform = OS, version = OBSIDIAN_VERSION env (default matching Ignis). Add a tower-http CompressionLayer so responses (bootstrap/tree) are gzip/br-compressed per Accept-Encoding (Ignis compresses too). VERIFY (axum oneshot tests): vault/list + vault/info shapes; bootstrap returns all six keys with the correct nested shapes and the live tree; unknown vault handled. clippy -D warnings + cargo test green; keel validate + guard green."; }
        part storyBootstrapVaultDoDR1 : TestResult { :>> id = "a0a83f81-5d11-4806-b3ea-deebe1f84063"; :>> outcome = VerdictKind::pass; :>> judgedAgainst = "bdd8f40"; :>> judgedAt = "2026-06-30"; :>> judgedBy = "ai"; :>> notes = "vault/list + vault/info + /api/bootstrap in src/vault_routes.rs; shapes confirmed against Ignis c9656b8 source (id=name vault.js:36-40; platform node-style; settings=DEFAULTS settings.js:9-20; version=OBSIDIAN_VERSION env default 1.12.7; bundle 6 keys bootstrap.js:136-152). tower-http CompressionLayer added. 41 tests pass (6 new), clippy + fmt clean. Accepted minor parity (documented, not new issues): default-vault is sorted-first vs Ignis readdir-first (arbitrary either way); CompressionLayer vs Ignis's pre-compress-cache (functionally equal, not byte-identical). Also fixed reverify.toml to target server/Cargo.toml (shipped default assumed a root workspace)."; }
        part storyBootstrapVaultDoDR2 : TestResult { :>> id = "2567fbed-7756-4cbb-9b8e-3db9a0395dc5"; :>> outcome = VerdictKind::pass; :>> judgedAgainst = "3b97ec1"; :>> judgedAt = "2026-07-02"; :>> judgedBy = "ai"; }
        part storyBootstrapVaultDoDR3 : TestResult { :>> id = "5ae5332f-f90b-443a-9f06-ee13f2dffd22"; :>> outcome = VerdictKind::pass; :>> judgedAgainst = "4cd1b2a"; :>> judgedAt = "2026-07-02"; :>> judgedBy = "ai"; }
        part storyBootstrapVaultDoDR4 : TestResult { :>> id = "79536a8e-7cd3-4645-9cec-ac8b966eaa8f"; :>> outcome = VerdictKind::pass; :>> judgedAgainst = "cb32d15"; :>> judgedAt = "2026-07-02"; :>> judgedBy = "claudeOpus"; }
        part storyBootstrapVaultDoDR5 : TestResult { :>> id = "64be52ba-6e81-4407-be05-97c39648be85"; :>> outcome = VerdictKind::pass; :>> judgedAgainst = "4a31e34"; :>> judgedAt = "2026-07-02"; :>> judgedBy = "claudeOpus"; }
        part storyBootstrapVaultDoDR6 : TestResult { :>> id = "cd60e018-fad3-4b6f-a3d2-19077eb4a861"; :>> outcome = VerdictKind::pass; :>> judgedAgainst = "6e90b2a"; :>> judgedAt = "2026-07-02"; :>> judgedBy = "claudeOpus"; }
        part storyBootstrapVaultDoDR7 : TestResult { :>> id = "9fe2eede-0b45-411f-a18f-e2e8f9c9df61"; :>> outcome = VerdictKind::pass; :>> judgedAgainst = "ceca03b"; :>> judgedAt = "2026-07-02"; :>> judgedBy = "claudeOpus"; }
        part storyBootstrapVaultDoDR8 : TestResult { :>> id = "9e2f338d-2429-44bb-a6ca-bbc7cbefadf9"; :>> outcome = VerdictKind::pass; :>> judgedAgainst = "da685ef"; :>> judgedAt = "2026-07-02"; :>> judgedBy = "claudeOpus"; }
        part storyBootstrapVaultDoDR9 : TestResult { :>> id = "5e4ca9d1-c744-4667-a879-13c62ba93f7d"; :>> outcome = VerdictKind::pass; :>> judgedAgainst = "9f29e89"; :>> judgedAt = "2026-07-02"; :>> judgedBy = "claudeOpus"; }
    }

    verification bootstrapVaultRefineGate : Test { :>> id = "8a8fedb7-414a-47e7-b4b9-83e1b6d7cd9b"; :>> title = "Sprint 8 refine gate (DoR)"; :>> createdAt = "2026-06-30"; :>> createdBy = "ai"; :>> method = VerificationMethod::inspect; :>> procedureText = "DoR: the read-only cold-start surface of srWireCompat. Shapes known from the c9656b8 inventory + source. Scoped to read-only (list/info/bootstrap) - no registry-mutability refactor (create/rename/remove is sprint09). INVEST: Independent (reads the existing registry + warm index); Valuable (the bundle Obsidian fetches on load - critical-path to loading the app); Estimable (5pts - 3 routes + compression); Small; Testable (oneshot). DoR met."; }
    part bootstrapVaultRefineGateR1 : TestResult { :>> id = "5d3b2287-f2f2-4211-bf06-109728b74b02"; :>> outcome = VerdictKind::pass; :>> judgedAgainst = "0fdf423"; :>> judgedAt = "2026-06-30"; :>> judgedBy = "ai"; }
    verification bootstrapVaultStandupGate : Test { :>> id = "8c5d7aac-c2fd-46df-a483-858588b61385"; :>> title = "Sprint 8 standup gate"; :>> createdAt = "2026-06-30"; :>> createdBy = "ai"; :>> method = VerificationMethod::inspect; :>> procedureText = "Approach: a routes/vault module: vault/list + vault/info from the registry (id per Ignis vault.js, platform=OS, version=OBSIDIAN_VERSION env); /api/bootstrap assembles {vault,vaultList,tree(from warm index),plugins:[],virtualPlugins:[],settings:defaults}; add tower-http CompressionLayer to the router. TDD each with axum oneshot. No blockers; implement gate pends the build."; }
    part bootstrapVaultStandupGateR1 : TestResult { :>> id = "746c53ab-5a1e-438b-9ed8-c4adfa0f75dd"; :>> outcome = VerdictKind::pass; :>> judgedAgainst = "0fdf423"; :>> judgedAt = "2026-06-30"; :>> judgedBy = "ai"; }
    verification bootstrapVaultImplementGate : Test { :>> id = "1c82f6df-8eb1-4f53-bb79-30cb760f9bec"; :>> title = "Sprint 8 implement gate"; :>> createdAt = "2026-06-30"; :>> createdBy = "ai"; :>> method = VerificationMethod::test; :>> procedureText = "Built test-first (6 new tests watched RED at todo!()). vault/list, vault/info (+404, default), full bootstrap bundle (+404). 41 tests pass; clippy -D warnings + fmt clean. Verified live at bdd8f40. Shapes confirmed against Ignis source (not guessed)."; }
    part bootstrapVaultImplementGateR1 : TestResult { :>> id = "ac8a5f18-78b7-440d-9912-8df3efc875c0"; :>> outcome = VerdictKind::pass; :>> judgedAgainst = "bdd8f40"; :>> judgedAt = "2026-06-30"; :>> judgedBy = "ai"; }
    verification bootstrapVaultReviewGate : Test { :>> id = "287e7819-6525-46d7-a587-4fa09dca9786"; :>> title = "Sprint 8 review gate"; :>> createdAt = "2026-06-30"; :>> createdBy = "ai"; :>> method = VerificationMethod::inspect; :>> procedureText = "Reviewed: every field derived from the Ignis source with quoted evidence (id/name/path/platform/version/settings/bundle) - genuine wire-parity, not guesswork; tree reuses tree_to_value (same shape as fs/tree); CompressionLayer covers all responses. Accepted minor parity differences documented (default-vault sort order; compress-per-request vs pre-compress-cache) - neither shim-breaking. Sound. Bonus: fixed a latent reverify.toml gap (root workspace assumption)."; }
    part bootstrapVaultReviewGateR1 : TestResult { :>> id = "d9dbcccb-8944-4c09-8085-dce55aec6713"; :>> outcome = VerdictKind::pass; :>> judgedAgainst = "bdd8f40"; :>> judgedAt = "2026-06-30"; :>> judgedBy = "ai"; }
    verification bootstrapVaultCloseOutGate : Test { :>> id = "cc3ebb86-88d5-4998-8387-e913ea8cfcf5"; :>> title = "Sprint 8 closeOut gate (autonomous, D0049)"; :>> createdAt = "2026-06-30"; :>> createdBy = "ai"; :>> method = VerificationMethod::inspect; :>> procedureText = "Autonomous closeOut (D0049): DoD pass; the cold-start bundle + read-only vault ops are built. cargo test (41) + clippy + keel validate/guard green. Remaining for a loadable app: static + Obsidian-bundle serving; vault create/rename/remove (sprint09)."; }
    part bootstrapVaultCloseOutGateR1 : TestResult { :>> id = "df16f34c-66b7-44e5-8db3-a0b629ea90e7"; :>> outcome = VerdictKind::pass; :>> judgedAgainst = "bdd8f40"; :>> judgedAt = "2026-06-30"; :>> judgedBy = "ai"; }
    verification bootstrapVaultRetroGate : Test { :>> id = "8a7c8926-9b32-4859-a838-27103165b760"; :>> title = "Sprint 8 retro gate (autonomous, D0049)"; :>> createdAt = "2026-06-30"; :>> createdBy = "ai"; :>> method = VerificationMethod::analyze; :>> procedureText = "Autonomous retro (D0049). WELL: reading the Ignis source for the exact id/settings/bundle shapes (not guessing) gave real wire-parity + quoted evidence; the bundle's tree reused tree_to_value for free. AVOIDABLE-ISSUE SCAN: no new tracked issues - the two parity differences (default-vault sort order; compress-per-request vs pre-compress-cache) are accepted as non-shim-breaking + documented in the review; a latent reverify.toml gap (assumed a root Cargo.toml) was found + fixed to target server/. LESSON: for a drop-in of a CLOSED upstream, deriving shapes from the reference source with quoted line evidence beats inferring from docs. Estimate 5pt held."; }
    part bootstrapVaultRetroGateR1 : TestResult { :>> id = "273d0f94-b243-4e12-b6e1-54c7170549a9"; :>> outcome = VerdictKind::pass; :>> judgedAgainst = "bdd8f40"; :>> judgedAt = "2026-06-30"; :>> judgedBy = "ai"; }
}
