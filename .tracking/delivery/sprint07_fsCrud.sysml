// IgniteDeliveryS07 — Sprint 7: the fs CRUD endpoints (read + write), wire-compatible with
// Ignis c9656b8, under srWireCompat. Applies dCritiqueCorrectness #3 (honest, durable writes -
// real mtime/size, no synthetic metadata, no coalescing). Writes propagate live via the
// existing notify watcher. PLANNED to standup; implement gate pends the build.
package IgniteDeliveryS07 {
    private import EngineElement::*;
    private import EngineWork::*;
    private import EngineVerification::*;
    private import EngineRelationships::*;

    // chartered by srWireCompat (IgniteRequirements); name-ref, no import.
    #CharteredBy dependency from fsCrudStory to srWireCompat;

    part fsCrudStory : Story {
        :>> id = "1aaabe14-302b-42cd-8d50-91aec8e58ab3";
        :>> title = "Sprint 7: fs CRUD endpoints (stat/readdir/readFile/writeFile/... ) - honest durable writes (srWireCompat)";
        :>> createdAt = "2026-06-30"; :>> createdBy = "will"; :>> kind = WorkKind::code; :>> priority = WorkPriority::p0; :>> owner = "ai"; :>> estimatedPoints = 8;
    }

    action def DeliveryRunS07 {
        action storyFsCrud;
        verification storyFsCrudDoD : Test { :>> id = "a41b2022-517d-4a04-8307-a5fbb72545a5"; :>> method = VerificationMethod::test; :>> procedureText = "Implement the fs CRUD routes wire-compatible with Ignis c9656b8: GET /api/fs/stat -> {type,size,mtime,ctime}; GET /api/fs/readdir -> [{name,type}]; GET /api/fs/readFile (encoding param; text or binary); POST /api/fs/writeFile {path,content,encoding?,base64?} -> {ok,mtime,size}; POST /api/fs/appendFile -> {ok}; POST /api/fs/mkdir {path,recursive?} -> {ok}; POST /api/fs/rename {oldPath,newPath} -> {ok}; POST /api/fs/copyFile {src,dest} -> {ok}; DELETE /api/fs/unlink|rmdir|rm(recursive) -> {ok}; GET /api/fs/access -> {ok}; POST /api/fs/utimes -> {ok}; POST /api/fs/batch-read {paths[]} -> {files:{relPath:content}}. CONSTRAINTS: (a) every path resolved WITHIN the vault (reject traversal / leading-slash escape); (b) dCritiqueCorrectness #3 - writeFile does a real write and returns the REAL mtime/size from the actual write (no synthetic metadata, no coalescing acked-before-disk); (c) writes are picked up by the existing live watcher (event-based, no manual index mutation) so the index + WS stay correct. VERIFY (axum oneshot tests + tempdir vault): each endpoint's status + shape matches Ignis; write then stat/readFile round-trips; traversal attempt rejected; a write is reflected in the live index/tree. clippy -D warnings + cargo test green; keel validate + guard green. (download + download-zip are a later sprint.)"; }
        part storyFsCrudDoDR1 : TestResult { :>> id = "29a9f2f0-5f30-4267-ab60-b797ee91d953"; :>> outcome = VerdictKind::pass; :>> judgedAgainst = "272821d"; :>> judgedAt = "2026-06-30"; :>> judgedBy = "ai"; :>> notes = "14 fs routes in src/fs_routes.rs, exact Ignis c9656b8 shapes. resolve_in_vault rejects traversal/absolute (tested read+write). writeFile: real write -> sync_all -> REAL mtime/size (dCritiqueCorrectness #3); no coalescing/synthetic. Handlers never touch the index; live watcher propagates. Errors sanitized. 35 tests pass (11 fs), clippy + fmt clean. Caveats: download/zip deferred (later sprint); blocking std::fs on async -> issue008 (Low); parent-dir fsync not done (Windows); ctime issue002 unchanged."; }
        part storyFsCrudDoDR2 : TestResult { :>> id = "a91de54c-bb4c-4d68-a64e-e4dc8f706da0"; :>> outcome = VerdictKind::pass; :>> judgedAgainst = "bdd8f40"; :>> judgedAt = "2026-06-30"; :>> judgedBy = "ai"; }
        part storyFsCrudDoDR3 : TestResult { :>> id = "7a1ef236-e2ed-4c8b-9b8e-3db9979fee95"; :>> outcome = VerdictKind::pass; :>> judgedAgainst = "3b97ec1"; :>> judgedAt = "2026-07-02"; :>> judgedBy = "ai"; }
        part storyFsCrudDoDR4 : TestResult { :>> id = "e5b591bc-848e-4787-ae69-6e42be22cb94"; :>> outcome = VerdictKind::pass; :>> judgedAgainst = "cb32d15"; :>> judgedAt = "2026-07-02"; :>> judgedBy = "claudeOpus"; }
        part storyFsCrudDoDR5 : TestResult { :>> id = "d12079e8-763c-4549-8f82-597abde9164e"; :>> outcome = VerdictKind::pass; :>> judgedAgainst = "4a31e34"; :>> judgedAt = "2026-07-02"; :>> judgedBy = "claudeOpus"; }
        part storyFsCrudDoDR6 : TestResult { :>> id = "39c30747-028e-4cb1-b54e-dabea6933d5e"; :>> outcome = VerdictKind::pass; :>> judgedAgainst = "6e90b2a"; :>> judgedAt = "2026-07-02"; :>> judgedBy = "claudeOpus"; }
        part storyFsCrudDoDR7 : TestResult { :>> id = "78a73d3a-1abb-43a3-8489-66574c28b583"; :>> outcome = VerdictKind::pass; :>> judgedAgainst = "ceca03b"; :>> judgedAt = "2026-07-02"; :>> judgedBy = "claudeOpus"; }
        part storyFsCrudDoDR8 : TestResult { :>> id = "76f381e9-339f-473f-89c4-3f361bd3a397"; :>> outcome = VerdictKind::pass; :>> judgedAgainst = "da685ef"; :>> judgedAt = "2026-07-02"; :>> judgedBy = "claudeOpus"; }
        part storyFsCrudDoDR9 : TestResult { :>> id = "a3731f5b-de75-4a2d-9cef-58eba25cb8bc"; :>> outcome = VerdictKind::pass; :>> judgedAgainst = "9f29e89"; :>> judgedAt = "2026-07-02"; :>> judgedBy = "claudeOpus"; }
    }

    verification fsCrudRefineGate : Test { :>> id = "f629957e-1a02-4c50-97ea-50d65e5999a0"; :>> title = "Sprint 7 refine gate (DoR)"; :>> createdAt = "2026-06-30"; :>> createdBy = "ai"; :>> method = VerificationMethod::inspect; :>> procedureText = "DoR: the fs CRUD half of srWireCompat. Route shapes known from the c9656b8 inventory; dCritiqueCorrectness #3 (honest durable writes) + within-vault path security are explicit criteria. INVEST: Independent (adds routes on the existing app + index); Valuable (Obsidian can read + SAVE through Ignite); Estimable (8pts - ~14 mechanical routes + path guard + write honesty); Small-ish (one sprint; download/zip deferred); Testable (per-route oneshot tests). DoR met."; }
    part fsCrudRefineGateR1 : TestResult { :>> id = "96cef2d2-bfab-4fae-ad44-d05d7cca753e"; :>> outcome = VerdictKind::pass; :>> judgedAgainst = "c692f79"; :>> judgedAt = "2026-06-30"; :>> judgedBy = "ai"; }
    verification fsCrudStandupGate : Test { :>> id = "85914ffd-0d4a-4aee-8e89-c6e75958e1bf"; :>> title = "Sprint 7 standup gate"; :>> createdAt = "2026-06-30"; :>> createdBy = "ai"; :>> method = VerificationMethod::inspect; :>> procedureText = "Approach: a routes/fs module + a resolve_in_vault(vault, rel) -> PathBuf guard (reject traversal); each handler maps to std::fs / tokio::fs with the exact Ignis JSON shape; writeFile returns real fs metadata post-write (fsync for durability). No write-coalescing. Rely on the live watcher for index/WS propagation. TDD each route with axum oneshot + a tempdir vault. No blockers; implement gate pends the build."; }
    part fsCrudStandupGateR1 : TestResult { :>> id = "99442cff-ac84-4710-b2ba-f0996f80e65b"; :>> outcome = VerdictKind::pass; :>> judgedAgainst = "c692f79"; :>> judgedAt = "2026-06-30"; :>> judgedBy = "ai"; }
    verification fsCrudImplementGate : Test { :>> id = "a803c9b8-0f9a-4ba5-9be8-e85fdc5a24ce"; :>> title = "Sprint 7 implement gate"; :>> createdAt = "2026-06-30"; :>> createdBy = "ai"; :>> method = VerificationMethod::test; :>> procedureText = "Built test-first (write_file watched RED at todo!() then GREEN). 14 routes; 35 tests pass (11 fs: stat/readdir/readFile+dir-error/writeFile-real-metadata/base64/append/mkdir/rename/copy/unlink/rm/access/utimes/batch-read + traversal-rejected). clippy -D warnings + fmt clean. Verified live at 272821d."; }
    part fsCrudImplementGateR1 : TestResult { :>> id = "2687dbf8-2b41-440a-85f4-109db4048b4d"; :>> outcome = VerdictKind::pass; :>> judgedAgainst = "272821d"; :>> judgedAt = "2026-06-30"; :>> judgedBy = "ai"; }
    verification fsCrudReviewGate : Test { :>> id = "c6f358fa-358a-455d-a932-19c2f9147d3c"; :>> title = "Sprint 7 review gate"; :>> createdAt = "2026-06-30"; :>> createdBy = "ai"; :>> method = VerificationMethod::inspect; :>> procedureText = "Reviewed: shapes match Ignis c9656b8; resolve_in_vault is a proper component-walk guard (rejects .. and absolute/drive paths), applied to every path field + tested; dCritiqueCorrectness #3 honored (real write -> fsync -> real mtime/size, no coalescing/synthetic); handlers stay out of the index (watcher propagates - consistent with the live-sync design); errors sanitized. Sound. Honest residual: blocking std::fs on async -> issue008 (Low), not a defect for single-file ops."; }
    part fsCrudReviewGateR1 : TestResult { :>> id = "968b3518-c84d-42d2-9cf2-6c29fb7bbf41"; :>> outcome = VerdictKind::pass; :>> judgedAgainst = "272821d"; :>> judgedAt = "2026-06-30"; :>> judgedBy = "ai"; }
    verification fsCrudCloseOutGate : Test { :>> id = "ce4a4a25-507b-44f0-9a28-e8a101c3fdd4"; :>> title = "Sprint 7 closeOut gate (autonomous, D0049)"; :>> createdAt = "2026-06-30"; :>> createdBy = "ai"; :>> method = VerificationMethod::inspect; :>> procedureText = "Autonomous closeOut (D0049): DoD pass; Obsidian can now read + SAVE through Ignite (14 fs routes, honest durable writes). cargo test (35) + clippy + keel validate/guard green. download/zip + vault CRUD + bootstrap + static remain toward full srWireCompat."; }
    part fsCrudCloseOutGateR1 : TestResult { :>> id = "f04c4545-333c-4dc0-b6c6-cea8b83a6bb3"; :>> outcome = VerdictKind::pass; :>> judgedAgainst = "272821d"; :>> judgedAt = "2026-06-30"; :>> judgedBy = "ai"; }
    verification fsCrudRetroGate : Test { :>> id = "47494a60-3531-422c-971d-30031fe3c627"; :>> title = "Sprint 7 retro gate (autonomous, D0049)"; :>> createdAt = "2026-06-30"; :>> createdBy = "ai"; :>> method = VerificationMethod::analyze; :>> procedureText = "Autonomous retro (D0049). WELL: the live-index design paid off again - fs write handlers needed ZERO index/WS wiring because the watcher already propagates real file changes; dCritiqueCorrectness #3 was straightforward (write -> fsync -> real stat). AVOIDABLE-ISSUE SCAN -> issue008 (blocking std::fs on the async runtime -> spawn_blocking refinement, Low; not HoL-blocking for single-file ops). LESSON: building the event-based live index first made the write side trivial + automatically consistent - ordering the sprints (read/index/watch before write) compounded. Estimate 8pt held."; }
    part fsCrudRetroGateR1 : TestResult { :>> id = "7c7686fa-f6dd-44a0-ac1e-0f8c789551e2"; :>> outcome = VerdictKind::pass; :>> judgedAgainst = "272821d"; :>> judgedAt = "2026-06-30"; :>> judgedBy = "ai"; }
}
