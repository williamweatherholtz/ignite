// IgniteDeliveryS06 — Sprint 6: WebSocket live sync (the WS half of srLiveSync). Puts the
// live index's change events on the wire to the browser, wire-compatible with Ignis c9656b8,
// applying dCritiqueEfficiency #5 (serialize once, backpressure, batch). PLANNED to standup;
// implement gate pends the build.
package IgniteDeliveryS06 {
    private import EngineElement::*;
    private import EngineWork::*;
    private import EngineVerification::*;
    private import EngineRelationships::*;

    // chartered by srLiveSync (IgniteRequirements); name-ref, no import.
    #CharteredBy dependency from wsLiveSyncStory to srLiveSync;

    part wsLiveSyncStory : Story {
        :>> id = "05bf316d-3f88-47fa-b2e4-9adc91268aff";
        :>> title = "Sprint 6: live sync over WebSocket - watcher events reach the browser (WS half of srLiveSync)";
        :>> createdAt = "2026-06-30"; :>> createdBy = "will"; :>> kind = WorkKind::code; :>> priority = WorkPriority::p0; :>> owner = "ai"; :>> estimatedPoints = 8;
    }

    action def DeliveryRunS06 {
        action storyWsLiveSync;
        verification storyWsLiveSyncDoD : Test { :>> id = "7653afef-37f1-40df-9c49-eaa6fda52922"; :>> method = VerificationMethod::test; :>> procedureText = "Live file changes reach connected browsers over WebSocket, wire-compatible with Ignis c9656b8, completing srLiveSync. (1) /ws?vault=<v> upgrade (vault query required; unknown/missing vault rejected). (2) the live index's watcher publishes each applied change as a TYPED event and the server broadcasts it to all clients on that vault: { type: 'created'|'modified'|'deleted'|'folder-created', path: <posix rel>, stat?: { size, mtime, ctime } } (stat for created/modified). (3) client->server control messages handled: subscribe-channel / unsubscribe-channel. (4) 30s ping/pong heartbeat. (5) dCritiqueEfficiency #5: each event serialized ONCE (broadcast the serialized message, not per-client), send honors backpressure (a lagging client recovers/drops rather than buffering unboundedly), burst events coalesced (300ms watcher debounce + batched send). VERIFY (tests): a WS client connects with ?vault, a file is created/modified/deleted on disk, and the client receives the correctly-typed, correctly-shaped event within the bound; a 2nd client on the same vault also receives it; heartbeat observed. clippy -D warnings + cargo test green; keel validate + guard green."; }
        part storyWsLiveSyncDoDR1 : TestResult { :>> id = "9a4793a0-ca7e-4b2b-97c7-c2c0f1d43ac4"; :>> outcome = VerdictKind::pass; :>> judgedAgainst = "80d878e"; :>> judgedAt = "2026-06-30"; :>> judgedBy = "ai"; :>> notes = "24 tests pass (7 new WS integration via real tokio-tungstenite client: created/modified/deleted/folder-created shapes, unknown-vault 404, two-client fan-out, subscribe-channel). srLiveSync COMPLETE - live edits reach the browser. dCritiqueEfficiency #5 applied (serialize-once at broadcast, bounded broadcast + Lagged drop-oldest, 300ms debounce-coalesce). Caveats: 30s heartbeat + Lagged-recovery wired but not directly tested (impractical to test cheaply; by-construction); subscribe-channel tracked-not-consumed (plugin sprint); ctime issue002 unchanged."; }
        part storyWsLiveSyncDoDR2 : TestResult { :>> id = "1975ae26-1e30-410f-b648-236ce8248b4d"; :>> outcome = VerdictKind::pass; :>> judgedAgainst = "272821d"; :>> judgedAt = "2026-06-30"; :>> judgedBy = "ai"; }
        part storyWsLiveSyncDoDR3 : TestResult { :>> id = "93b1ee2d-1eb4-4860-a64e-e4dc894784f4"; :>> outcome = VerdictKind::pass; :>> judgedAgainst = "bdd8f40"; :>> judgedAt = "2026-06-30"; :>> judgedBy = "ai"; }
        part storyWsLiveSyncDoDR4 : TestResult { :>> id = "f0a599c6-d5f4-4c56-a6fb-874a091ee622"; :>> outcome = VerdictKind::pass; :>> judgedAgainst = "3b97ec1"; :>> judgedAt = "2026-07-02"; :>> judgedBy = "ai"; }
        part storyWsLiveSyncDoDR5 : TestResult { :>> id = "03a055a2-ab35-4dd1-85d9-36d68a326e01"; :>> outcome = VerdictKind::pass; :>> judgedAgainst = "cb32d15"; :>> judgedAt = "2026-07-02"; :>> judgedBy = "claudeOpus"; }
        part storyWsLiveSyncDoDR6 : TestResult { :>> id = "ef0b3dce-9ce3-4b93-a6f2-220e8ba3b747"; :>> outcome = VerdictKind::pass; :>> judgedAgainst = "4a31e34"; :>> judgedAt = "2026-07-02"; :>> judgedBy = "claudeOpus"; }
        part storyWsLiveSyncDoDR7 : TestResult { :>> id = "c40ff25b-30f0-443d-9e3b-650999c1ad14"; :>> outcome = VerdictKind::pass; :>> judgedAgainst = "6e90b2a"; :>> judgedAt = "2026-07-02"; :>> judgedBy = "claudeOpus"; }
        part storyWsLiveSyncDoDR8 : TestResult { :>> id = "02f4284e-491d-4b30-a208-a711c699dbd0"; :>> outcome = VerdictKind::pass; :>> judgedAgainst = "ceca03b"; :>> judgedAt = "2026-07-02"; :>> judgedBy = "claudeOpus"; }
        part storyWsLiveSyncDoDR9 : TestResult { :>> id = "6da2942b-69bc-400e-b8c0-41a7bf0ab2cd"; :>> outcome = VerdictKind::pass; :>> judgedAgainst = "da685ef"; :>> judgedAt = "2026-07-02"; :>> judgedBy = "claudeOpus"; }
        part storyWsLiveSyncDoDR10 : TestResult { :>> id = "72e67ffa-2408-457f-ba52-285c06c268d5"; :>> outcome = VerdictKind::pass; :>> judgedAgainst = "9f29e89"; :>> judgedAt = "2026-07-02"; :>> judgedBy = "claudeOpus"; }
    }

    verification wsLiveSyncRefineGate : Test { :>> id = "b3c92791-a76a-4c77-97d4-952993eddf68"; :>> title = "Sprint 6 refine gate (DoR)"; :>> createdAt = "2026-06-30"; :>> createdBy = "ai"; :>> method = VerificationMethod::inspect; :>> procedureText = "DoR: the WS half of srLiveSync, building on the sprint05 live index. Ignis /ws protocol known from the c9656b8 inventory; dCritiqueEfficiency #5 is an explicit acceptance criterion. INVEST: Independent (depends only on the now-built live index); Valuable (browsers finally see live updates - completes srLiveSync); Estimable (8pts - WS endpoint + per-vault broadcast wired to the watcher + heartbeat); Small (one sprint); Testable (WS integration tests). DoR met."; }
    part wsLiveSyncRefineGateR1 : TestResult { :>> id = "22b0b7d3-fdf7-49ec-9875-d00b9b2d69dd"; :>> outcome = VerdictKind::pass; :>> judgedAgainst = "2c0c489"; :>> judgedAt = "2026-06-30"; :>> judgedBy = "ai"; }
    verification wsLiveSyncStandupGate : Test { :>> id = "65b4961f-77c7-4143-9095-40b1a76612b3"; :>> title = "Sprint 6 standup gate"; :>> createdAt = "2026-06-30"; :>> createdBy = "ai"; :>> method = VerificationMethod::inspect; :>> procedureText = "Approach: give each VaultIndex a tokio broadcast::Sender<String>; apply_paths derives the typed event per path (exists+new=created/folder-created, exists+changed=modified, gone=deleted), serializes ONCE, and broadcasts the message text. An axum /ws handler resolves the vault, subscribes to its broadcast, selects over {recv -> ws.send, client msg -> subscribe-channel/pong, 30s ping}. Lagged receiver -> drop/recover. TDD with a real WS client (tokio-tungstenite) or axum test util. No blockers; implement gate pends the build."; }
    part wsLiveSyncStandupGateR1 : TestResult { :>> id = "9d0d7935-4b3a-4789-8f5e-d4b8fbee6237"; :>> outcome = VerdictKind::pass; :>> judgedAgainst = "2c0c489"; :>> judgedAt = "2026-06-30"; :>> judgedBy = "ai"; }
    verification wsLiveSyncImplementGate : Test { :>> id = "18d8bdd0-bb97-4cc6-aa36-a0a2fb78d18f"; :>> title = "Sprint 6 implement gate"; :>> createdAt = "2026-06-30"; :>> createdBy = "ai"; :>> method = VerificationMethod::test; :>> procedureText = "Built test-first. 24 tests pass: 7 WS integration (real ephemeral-port server + tokio-tungstenite client) covering created/modified/deleted/folder-created shapes, unknown-vault rejection, two-client fan-out, subscribe-channel; + 17 prior. clippy -D warnings clean; fmt. Verified live at 80d878e."; }
    part wsLiveSyncImplementGateR1 : TestResult { :>> id = "c547266b-07a4-4ff7-bca7-643e6438cf0c"; :>> outcome = VerdictKind::pass; :>> judgedAgainst = "80d878e"; :>> judgedAt = "2026-06-30"; :>> judgedBy = "ai"; }
    verification wsLiveSyncReviewGate : Test { :>> id = "144badfd-d80e-44cd-b933-3fa08941a119"; :>> title = "Sprint 6 review gate"; :>> createdAt = "2026-06-30"; :>> createdBy = "ai"; :>> method = VerificationMethod::inspect; :>> procedureText = "Reviewed: events serialized ONCE at broadcast (dCritiqueEfficiency #5, not per-client); event-type derived from presence-before-change x disk truth (correct created/modified/folder-created/deleted); shapes match Ignis c9656b8 exactly (a JS shim depends on this); unknown vault rejected before upgrade; bounded broadcast + Lagged drop-oldest avoids unbounded buffering. srLiveSync is complete end-to-end. Accepted test-coverage limits: 30s heartbeat + forced-Lagged are wired but verified by construction not test (impractical cheaply) - acceptable, not new defects. Sound."; }
    part wsLiveSyncReviewGateR1 : TestResult { :>> id = "4f61b591-7f8b-4d1b-9846-ef916ff09e88"; :>> outcome = VerdictKind::pass; :>> judgedAgainst = "80d878e"; :>> judgedAt = "2026-06-30"; :>> judgedBy = "ai"; }
    verification wsLiveSyncCloseOutGate : Test { :>> id = "03970657-e07c-454f-8a8a-1eeade10fa2b"; :>> title = "Sprint 6 closeOut gate (autonomous, D0049)"; :>> createdAt = "2026-06-30"; :>> createdBy = "ai"; :>> method = VerificationMethod::inspect; :>> procedureText = "Autonomous closeOut (D0049): DoD pass; srLiveSync is delivered end-to-end (live index + WS). cargo test (24) + clippy + keel validate/guard green."; }
    part wsLiveSyncCloseOutGateR1 : TestResult { :>> id = "2421424e-5118-4ad0-b300-e2fac1adfdfa"; :>> outcome = VerdictKind::pass; :>> judgedAgainst = "80d878e"; :>> judgedAt = "2026-06-30"; :>> judgedBy = "ai"; }
    verification wsLiveSyncRetroGate : Test { :>> id = "a7cdb7bb-031e-4c1f-bccf-6f37800b85ee"; :>> title = "Sprint 6 retro gate (autonomous, D0049)"; :>> createdAt = "2026-06-30"; :>> createdBy = "ai"; :>> method = VerificationMethod::analyze; :>> procedureText = "Autonomous retro (D0049). WELL: srLiveSync landed cleanly on the sprint05 live index - the broadcast hooked straight into apply_paths, and serialize-once fell out naturally (broadcast a String). The watcher's event-type derivation reused the presence-before-change info already needed for the COW update. AVOIDABLE-ISSUE SCAN: no new tracked issues - the heartbeat (30s) + Lagged-recovery paths are wired but verified by construction not automated test (accepted as impractical-to-test-cheaply, not defects); subscribe-channel consumption is deferred to the plugin sprint (tracked by scope, not a bug); issue002 ctime parity unchanged. LESSON: dCritiqueEfficiency #5's serialize-once is free when you broadcast the serialized form, not the event struct. Estimate 8pt held."; }
    part wsLiveSyncRetroGateR1 : TestResult { :>> id = "a068d432-528f-4298-a144-908d9eafd167"; :>> outcome = VerdictKind::pass; :>> judgedAgainst = "80d878e"; :>> judgedAt = "2026-06-30"; :>> judgedBy = "ai"; }
}
