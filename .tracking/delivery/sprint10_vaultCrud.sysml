// IgniteDeliveryS10 — Sprint 10: vault create/rename/remove (srWireCompat). Requires making
// VaultRegistry mutable at runtime (RwLock) so vaults can be added/dropped + their live
// watchers started/stopped. PLANNED to standup; implement gate pends the build.
package IgniteDeliveryS10 {
    private import EngineElement::*;
    private import EngineWork::*;
    private import EngineVerification::*;
    private import EngineRelationships::*;

    // chartered by srWireCompat (IgniteRequirements); name-ref, no import.
    #CharteredBy dependency from vaultCrudStory to srWireCompat;

    part vaultCrudStory : Story {
        :>> id = "588077f5-864a-4041-8885-db6a4c182b9d";
        :>> title = "Sprint 10: vault create/rename/remove - runtime-mutable VaultRegistry (srWireCompat)";
        :>> createdAt = "2026-07-02"; :>> createdBy = "will"; :>> kind = WorkKind::code; :>> priority = WorkPriority::p1; :>> owner = "ai"; :>> estimatedPoints = 8;
    }

    action def DeliveryRunS10 {
        action storyVaultCrud;
        verification storyVaultCrudDoD : Test { :>> id = "a3455fad-bdaf-459c-8168-e15a4845aa24"; :>> method = VerificationMethod::test; :>> procedureText = "Implement the vault-mutation routes wire-compatible with Ignis c9656b8 (check vault.js): POST /api/vault/create {name} -> {ok:true,id,path} (create dir + .obsidian subdir; add to registry as a LIVE index); POST /api/vault/rename {vault,name} -> {ok:true,id,path} (rename dir on disk; re-key the registry, watcher tracks the new path); DELETE /api/vault/remove?vault -> {ok:true} (recursively delete the dir; drop the index so its watcher stops). NAME VALIDATION must match Ignis vault.js:11-27: reject / \\ : * ? \" < > |, a leading '.', Windows reserved names (CON/PRN/AUX/NUL/COM1-9/LPT1-9), and > 255 chars (400). REGISTRY: make VaultRegistry interior-mutable (RwLock<HashMap<String, Arc<VaultIndex>>> or similar) so create/remove add/drop entries at runtime; get() returns an Arc snapshot; update every caller (fs_routes/vault_routes/static_routes/ws/app) accordingly, keeping all existing tests green. VERIFY (axum oneshot + tempdir vault-root): create makes a vault that then appears in vault/list + is readable via fs/tree; rename moves it + updates list; remove deletes it + drops it from list; invalid names rejected (400); the ~49 prior tests still pass. clippy -D warnings + cargo test green; keel validate + guard green."; }
        part storyVaultCrudDoDR1 : TestResult { :>> id = "f0a473ce-c16d-4b9d-941d-a4a8c4c800cf"; :>> outcome = VerdictKind::pass; :>> judgedAgainst = "4cd1b2a"; :>> judgedAt = "2026-07-02"; :>> judgedBy = "ai"; :>> notes = "VaultRegistry.vaults -> RwLock<HashMap<String,Arc<VaultIndex>>> + vault_root; get() returns an Arc snapshot (reads cheap); insert_vault/remove_vault (remove drops the Arc -> watcher stops). create/rename/remove in vault_routes; is_valid_vault_name matches vault.js:11-27 exactly. 56 tests pass (7 new: registry mutate, create, invalid-name, duplicate-409, rename, remove, unknown-404), clippy + fmt clean. No call-site edits needed (Arc deref). Accepted caveats (single-user self-host, not new issues): remove-while-a-client-holds-an-Arc stops the watcher only when that Arc drops (eventual); create/rename/remove not serialized vs concurrent identical calls (small TOCTOU)."; }
        part storyVaultCrudDoDR2 : TestResult { :>> id = "973e2e74-a37a-4c8f-b45c-751f6298550c"; :>> outcome = VerdictKind::pass; :>> judgedAgainst = "cb32d15"; :>> judgedAt = "2026-07-02"; :>> judgedBy = "claudeOpus"; }
        part storyVaultCrudDoDR3 : TestResult { :>> id = "57adcb2d-2935-42fb-8cbe-a352722b41eb"; :>> outcome = VerdictKind::pass; :>> judgedAgainst = "6e90b2a"; :>> judgedAt = "2026-07-02"; :>> judgedBy = "claudeOpus"; }
        part storyVaultCrudDoDR4 : TestResult { :>> id = "068458cc-1c4d-443d-a8d5-66a4df7c73b8"; :>> outcome = VerdictKind::pass; :>> judgedAgainst = "9f29e89"; :>> judgedAt = "2026-07-02"; :>> judgedBy = "claudeOpus"; }
    }

    verification vaultCrudRefineGate : Test { :>> id = "1969a91c-b848-4a6e-8c50-0c95334366c6"; :>> title = "Sprint 10 refine gate (DoR)"; :>> createdAt = "2026-07-02"; :>> createdBy = "ai"; :>> method = VerificationMethod::inspect; :>> procedureText = "DoR: vault mutation half of srWireCompat. Shapes + name rules from vault.js. Central change: runtime-mutable registry (RwLock). INVEST: Independent (extends the registry + routes); Valuable (vault management from the UI); Estimable (8pts - registry refactor touching all callers + 3 routes + validation); Small-ish (one sprint); Testable (oneshot). DoR met."; }
    part vaultCrudRefineGateR1 : TestResult { :>> id = "b0a4be3e-1947-415f-a083-4af1aa37e175"; :>> outcome = VerdictKind::pass; :>> judgedAgainst = "4f556a9"; :>> judgedAt = "2026-07-02"; :>> judgedBy = "ai"; }
    verification vaultCrudStandupGate : Test { :>> id = "fae01c75-b783-41f1-b026-bed08c845b53"; :>> title = "Sprint 10 standup gate"; :>> createdAt = "2026-07-02"; :>> createdBy = "ai"; :>> method = VerificationMethod::inspect; :>> procedureText = "Approach: refactor VaultRegistry to hold RwLock<HashMap<String, Arc<VaultIndex>>>; get()->Option<Arc<VaultIndex>>; add insert/remove; update all callers to the Arc snapshot. Add a vault-mutation handler set (create/rename/remove) with a validate_vault_name matching vault.js. create -> build_live + insert; remove -> remove (drops Arc -> watcher stops); rename -> fs rename + re-key. TDD each + a full-regression pass. No blockers; implement gate pends the build."; }
    part vaultCrudStandupGateR1 : TestResult { :>> id = "235e6e81-5a34-4ff6-9965-72dcfa74eedc"; :>> outcome = VerdictKind::pass; :>> judgedAgainst = "4f556a9"; :>> judgedAt = "2026-07-02"; :>> judgedBy = "ai"; }
    verification vaultCrudImplementGate : Test { :>> id = "c436e8ea-d7be-4b8b-ba66-789547347283"; :>> title = "Sprint 10 implement gate"; :>> createdAt = "2026-07-02"; :>> createdBy = "ai"; :>> method = VerificationMethod::test; :>> procedureText = "Built test-first (create route watched RED - absent route != 200 - then GREEN). Registry refactored to RwLock + Arc snapshots (no call-site edits). 56 tests pass (7 new: registry mutate, create, invalid-name, duplicate-409, rename, remove, unknown-404). clippy -D warnings + fmt clean. Verified live at 4cd1b2a."; }
    part vaultCrudImplementGateR1 : TestResult { :>> id = "f3087604-7d53-4379-9f78-343bf0f8e456"; :>> outcome = VerdictKind::pass; :>> judgedAgainst = "4cd1b2a"; :>> judgedAt = "2026-07-02"; :>> judgedBy = "ai"; }
    verification vaultCrudReviewGate : Test { :>> id = "8036cbbf-3768-4815-857e-ed563edefcf5"; :>> title = "Sprint 10 review gate"; :>> createdAt = "2026-07-02"; :>> createdBy = "ai"; :>> method = VerificationMethod::inspect; :>> procedureText = "Reviewed: RwLock<HashMap<String,Arc<VaultIndex>>> keeps reads cheap (read lock + Arc clone) so warm fs/tree is unaffected; remove drops the Arc so the watcher stops; rename = fs-rename + remove/insert (fresh live index). Name rules match vault.js:11-27 exactly (quoted); status codes match (409 dup/target, 404 unknown). Elegant that no call sites changed (Arc deref). Accepted single-user caveats (eventual watcher stop on remove-while-connected; TOCTOU on concurrent identical mutations) - documented, not shim-breaking. Sound."; }
    part vaultCrudReviewGateR1 : TestResult { :>> id = "9592a5e8-365f-427a-baa4-e8a84748df44"; :>> outcome = VerdictKind::pass; :>> judgedAgainst = "4cd1b2a"; :>> judgedAt = "2026-07-02"; :>> judgedBy = "ai"; }
    verification vaultCrudCloseOutGate : Test { :>> id = "fe824b55-2051-4f07-9c7b-40792c63ec99"; :>> title = "Sprint 10 closeOut gate (autonomous, D0049)"; :>> createdAt = "2026-07-02"; :>> createdBy = "ai"; :>> method = VerificationMethod::inspect; :>> procedureText = "Autonomous closeOut (D0049): DoD pass; vault management (create/rename/remove) works against a runtime-mutable registry. cargo test (56) + clippy + keel validate/guard green. Remaining srWireCompat: proxy, settings/version/plugins, download/zip, native headless-sync + deployment."; }
    part vaultCrudCloseOutGateR1 : TestResult { :>> id = "a63fd37a-aedd-4113-bf02-effea8f29cc3"; :>> outcome = VerdictKind::pass; :>> judgedAgainst = "4cd1b2a"; :>> judgedAt = "2026-07-02"; :>> judgedBy = "ai"; }
    verification vaultCrudRetroGate : Test { :>> id = "850c1ec7-ad1b-43f9-9c31-8ee26d6897f2"; :>> title = "Sprint 10 retro gate (autonomous, D0049)"; :>> createdAt = "2026-07-02"; :>> createdBy = "ai"; :>> method = VerificationMethod::analyze; :>> procedureText = "Autonomous retro (D0049). WELL: returning Arc<VaultIndex> from get() meant the RwLock refactor needed ZERO handler changes (deref just works) - a clean seam; Ignis's config.refreshVaults/invalidateVault have no analog because our live index is already current. AVOIDABLE-ISSUE SCAN: no new tracked issues - two caveats accepted for single-user self-host (eventual watcher stop when a client still holds the Arc; small TOCTOU on concurrent identical mutations) and documented in the review; not shim-breaking. LESSON: designing get() to hand out Arc snapshots (not references) is what made the store swappable without touching callers. Estimate 8pt held."; }
    part vaultCrudRetroGateR1 : TestResult { :>> id = "342a84d7-8f89-4aae-b26f-331d4c0d38d7"; :>> outcome = VerdictKind::pass; :>> judgedAgainst = "4cd1b2a"; :>> judgedAt = "2026-07-02"; :>> judgedBy = "ai"; }
}
