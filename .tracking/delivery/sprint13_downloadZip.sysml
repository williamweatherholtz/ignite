// IgniteDeliveryS13 — Sprint 13: /api/fs/download + /api/fs/download-zip (srWireCompat).
// The last fs endpoints; completes the fs surface. PLANNED to standup; implement gate pends build.
package IgniteDeliveryS13 {
    private import EngineElement::*;
    private import EngineWork::*;
    private import EngineVerification::*;
    private import EngineRelationships::*;

    #CharteredBy dependency from downloadStory to srWireCompat;

    part downloadStory : Story {
        :>> id = "11bda5d1-7470-40b1-8a2a-5d101701a697";
        :>> title = "Sprint 13: /api/fs/download (file) + /api/fs/download-zip (folder as ZIP) (srWireCompat)";
        :>> createdAt = "2026-07-02"; :>> createdBy = "will"; :>> kind = WorkKind::code; :>> priority = WorkPriority::p2; :>> owner = "ai"; :>> estimatedPoints = 3;
    }

    action def DeliveryRunS13 {
        action storyDownload;
        verification storyDownloadDoD : Test { :>> id = "8372f5da-9ee8-40a7-846b-9179581d3196"; :>> method = VerificationMethod::test; :>> procedureText = "Implement, wire-compatible with Ignis c9656b8 (check fs.js:529-597): GET /api/fs/download?vault&path -> the file bytes with Content-Disposition attachment (error 400/404 on a directory/missing); GET /api/fs/download-zip?vault&path -> the directory zipped (application/zip + Content-Disposition), SKIPPING symlinks (as Ignis does). Reuse resolve_in_vault (within-vault, traversal rejected). Add the `zip` crate. VERIFY (axum oneshot + tempdir vault): download returns a file's bytes + a Content-Disposition header; download on a dir errors; download-zip of a folder returns a valid zip whose entries match the folder's files (unzip in-test + assert); traversal rejected. clippy -D warnings + cargo test green; keel validate + guard green."; }
        part storyDownloadDoDR1 : TestResult { :>> id = "0c8cccbb-d843-4c41-b53e-f1f58a331742"; :>> outcome = VerdictKind::pass; :>> judgedAgainst = "6e90b2a"; :>> judgedAt = "2026-07-02"; :>> judgedBy = "ai"; :>> notes = "fs_routes download (file bytes + Content-Disposition; dir->400; missing->404) + download-zip (application/zip, folder-name-prefixed entries per fs.js:588, symlinks skipped via symlink_metadata) using the zip crate; both reuse resolve_in_vault. 74 tests pass (5 new, incl. in-test unzip verifying entries), clippy + fmt clean. Matches fs.js:529-597. Caveats: the zip is buffered fully in memory (Vec<u8>), not streamed like Ignis's archive.pipe -> issue011 (Low); Content-Disposition is basic ASCII filename= (no RFC-5987 filename* for non-ASCII names like Ignis) -> issue012 (Low)."; }
        part storyDownloadDoDR2 : TestResult { :>> id = "0c45160c-1300-4261-b30c-a4a02443a1a2"; :>> outcome = VerdictKind::pass; :>> judgedAgainst = "ceca03b"; :>> judgedAt = "2026-07-02"; :>> judgedBy = "claudeOpus"; }
        part storyDownloadDoDR3 : TestResult { :>> id = "0a915abb-2be4-45fd-b847-7d7ef45c1856"; :>> outcome = VerdictKind::pass; :>> judgedAgainst = "da685ef"; :>> judgedAt = "2026-07-02"; :>> judgedBy = "claudeOpus"; }
        part storyDownloadDoDR4 : TestResult { :>> id = "3710f82d-d6ba-48eb-8b72-97347b177ebb"; :>> outcome = VerdictKind::pass; :>> judgedAgainst = "9f29e89"; :>> judgedAt = "2026-07-02"; :>> judgedBy = "claudeOpus"; }
    }

    verification downloadRefineGate : Test { :>> id = "501564d3-a7c0-4420-9ce9-8ab61a043d53"; :>> title = "Sprint 13 refine gate (DoR)"; :>> createdAt = "2026-07-02"; :>> createdBy = "ai"; :>> method = VerificationMethod::inspect; :>> procedureText = "DoR: the last fs endpoints of srWireCompat. Shapes from fs.js:529-597. INVEST: Independent (adds 2 routes; reuses the path guard); Valuable (file/folder export); Estimable (3pts - 2 routes + zip); Small; Testable (oneshot + in-test unzip). DoR met."; }
    part downloadRefineGateR1 : TestResult { :>> id = "810ca3a0-4c01-4db3-a750-17434602ee02"; :>> outcome = VerdictKind::pass; :>> judgedAgainst = "60b3cff"; :>> judgedAt = "2026-07-02"; :>> judgedBy = "ai"; }
    verification downloadStandupGate : Test { :>> id = "cd0fee3d-3f92-4ad4-8c4e-fb291508b1cc"; :>> title = "Sprint 13 standup gate"; :>> createdAt = "2026-07-02"; :>> createdBy = "ai"; :>> method = VerificationMethod::inspect; :>> procedureText = "Approach: add to fs_routes (or a small module): download reads the file + sets Content-Disposition; download-zip walks the dir (skip symlinks), streams entries into a zip (zip crate) with Content-Disposition. Reuse resolve_in_vault. TDD with oneshot + an in-test unzip assertion. No blockers; implement gate pends the build."; }
    part downloadStandupGateR1 : TestResult { :>> id = "027a54be-c741-44bf-9fd5-74b97bef3a28"; :>> outcome = VerdictKind::pass; :>> judgedAgainst = "60b3cff"; :>> judgedAt = "2026-07-02"; :>> judgedBy = "ai"; }
    verification downloadImplementGate : Test { :>> id = "105ca9a8-b62a-4c10-a6d1-faee65c950b3"; :>> title = "Sprint 13 implement gate"; :>> createdAt = "2026-07-02"; :>> createdBy = "ai"; :>> method = VerificationMethod::test; :>> procedureText = "Built test-first (5 tests RED at not-implemented then GREEN). 74 tests pass: download bytes+disposition, download dir-400 + missing-404, download-zip prefixed-entries (unzipped in-test), download-zip non-dir-400, traversal-rejected. clippy -D warnings + fmt clean. Verified live at 6e90b2a."; }
    part downloadImplementGateR1 : TestResult { :>> id = "cb99bb61-668f-443f-b61b-b3f388031698"; :>> outcome = VerdictKind::pass; :>> judgedAgainst = "6e90b2a"; :>> judgedAt = "2026-07-02"; :>> judgedBy = "ai"; }
    verification downloadReviewGate : Test { :>> id = "7bbf091a-bc7b-4975-937e-c0a09d56dfe8"; :>> title = "Sprint 13 review gate"; :>> createdAt = "2026-07-02"; :>> createdBy = "ai"; :>> method = VerificationMethod::inspect; :>> procedureText = "Reviewed: download/download-zip match fs.js:529-597 (dir->400, non-dir->400, folder-name-prefixed zip entries, symlinks skipped); reuse the audited path guard; zip entries verified by in-test unzip. Two honest Low residuals logged (issue011 zip-in-memory not streamed; issue012 Content-Disposition ASCII-only vs Ignis's RFC-5987). Sound; completes the fs surface."; }
    part downloadReviewGateR1 : TestResult { :>> id = "9ee3e17c-f37e-490c-bd77-1ea544fa04c7"; :>> outcome = VerdictKind::pass; :>> judgedAgainst = "6e90b2a"; :>> judgedAt = "2026-07-02"; :>> judgedBy = "ai"; }
    verification downloadCloseOutGate : Test { :>> id = "bab4269b-e324-451e-a1be-4be6637917b4"; :>> title = "Sprint 13 closeOut gate (autonomous, D0049)"; :>> createdAt = "2026-07-02"; :>> createdBy = "ai"; :>> method = VerificationMethod::inspect; :>> procedureText = "Autonomous closeOut (D0049): DoD pass; the fs surface is complete (CRUD + download + zip). cargo test (74) + clippy + keel validate/guard green. Remaining srWireCompat: native headless-sync (dPlugins); then deployment (Dockerfile + Obsidian bundle + Ignis JS)."; }
    part downloadCloseOutGateR1 : TestResult { :>> id = "8866466a-b1ea-44d5-94f6-bb5330c1551e"; :>> outcome = VerdictKind::pass; :>> judgedAgainst = "6e90b2a"; :>> judgedAt = "2026-07-02"; :>> judgedBy = "ai"; }
    verification downloadRetroGate : Test { :>> id = "b237a6e5-1fa6-44cd-bc9d-04e89b1eff5c"; :>> title = "Sprint 13 retro gate (autonomous, D0049)"; :>> createdAt = "2026-07-02"; :>> createdBy = "ai"; :>> method = VerificationMethod::analyze; :>> procedureText = "Autonomous retro (D0049). WELL: small sprint, in-test unzip gave real confidence the zip entries match; reusing resolve_in_vault + fs.js line-matching kept it faithful. AVOIDABLE-ISSUE SCAN -> issue011 (zip buffered in memory, not streamed - Low, akin to issue008's spawn-blocking), issue012 (Content-Disposition ASCII-only, no RFC-5987 filename* - Low wire-parity for non-ASCII names). LESSON: buffering-vs-streaming and header-encoding edge cases are the usual honest residuals of a fast first cut - track them, don't gold-plate mid-sprint. Estimate 3pt held. The full ~32-route surface (minus native server plugins) now has a Rust analog."; }
    part downloadRetroGateR1 : TestResult { :>> id = "bc731db2-e86b-47bd-abb6-5ddba5a2ed00"; :>> outcome = VerdictKind::pass; :>> judgedAgainst = "6e90b2a"; :>> judgedAt = "2026-07-02"; :>> judgedBy = "ai"; }
}
