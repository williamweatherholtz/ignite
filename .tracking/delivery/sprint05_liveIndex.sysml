// IgniteDeliveryS05 — Sprint 5: the LIVE INDEX (the index half of srLiveSync). A notify
// watcher keeps the warm VaultIndex correct as files change, honoring dCritiqueCorrectness
// (#1 continuous-watch + reconcile; #2 event-based incremental invalidation). The WebSocket
// delivery layer is sprint06. PLANNED to standup; implement gate pends the build.
package IgniteDeliveryS05 {
    private import EngineElement::*;
    private import EngineWork::*;
    private import EngineVerification::*;
    private import EngineRelationships::*;

    // chartered by srLiveSync (IgniteRequirements); name-ref, no import.
    #CharteredBy dependency from liveIndexStory to srLiveSync;

    part liveIndexStory : Story {
        :>> id = "9d788f2d-a076-4cac-9e49-e7d199dc95ea";
        :>> title = "Sprint 5: live index - notify watcher keeps the warm index correct (index half of srLiveSync)";
        :>> createdAt = "2026-06-30"; :>> createdBy = "will"; :>> kind = WorkKind::code; :>> priority = WorkPriority::p0; :>> owner = "ai"; :>> estimatedPoints = 8;
    }

    action def DeliveryRunS05 {
        action storyLiveIndex;
        verification storyLiveIndexDoD : Test { :>> id = "339131c5-3587-474c-8552-5e08b9c29244"; :>> method = VerificationMethod::test; :>> procedureText = "The warm VaultIndex stays correct as the filesystem changes, per dCritiqueCorrectness. (1) a notify-based watcher starts when the index is built and runs CONTINUOUSLY (NOT gated on WS clients) for the index's lifetime; (2) on create/modify/delete/rename/folder events the index updates the affected entry INCREMENTALLY (no full re-walk), keyed on REAL file events (not dir-mtime); (3) on watcher start/restart the index RECONCILES against disk (re-diff) so it can never silently diverge; (4) burst events are debounced (~300ms, matching Ignis awaitWriteFinish). The index must stay thread-safe with lock-free or low-contention reads so warm GET /api/fs/tree stays < 50ms. VERIFY (tests): create -> entry appears; modify -> size/mtime update; delete -> entry gone; rename -> old gone + new present; a change made while the watcher is (re)started is reconciled (no silent divergence); GET /api/fs/tree reflects each within the debounce bound. clippy -D warnings + cargo test green; keel validate + guard green."; }
        part storyLiveIndexDoDR1 : TestResult { :>> id = "4727ca03-81ef-4878-b3a8-18ebeacf034e"; :>> outcome = VerdictKind::pass; :>> judgedAgainst = "882a80e"; :>> judgedAt = "2026-06-30"; :>> judgedBy = "ai"; :>> notes = "VaultIndex -> Arc<ArcSwap<Tree>> (lock-free reads); build_live arms a notify-debouncer (300ms) before the authoritative reconcile() walk; apply_paths re-stats only changed paths (COW upsert/remove, atomic store). 17 tests pass (6 live: create/modify/delete/rename/dir + reconcile-after-missed-change; + app live-reflection regression), clippy clean. dCritiqueCorrectness #1+#2 satisfied. Caveats tracked: issue006 (no watcher auto-restart), issue007 (bulk-move subtree under-population)."; }
        part storyLiveIndexDoDR2 : TestResult { :>> id = "2cb1c7c2-86c2-409e-87ac-6c1ca9614fd6"; :>> outcome = VerdictKind::pass; :>> judgedAgainst = "80d878e"; :>> judgedAt = "2026-06-30"; :>> judgedBy = "ai"; }
        part storyLiveIndexDoDR3 : TestResult { :>> id = "0481201f-dddc-4c8b-b648-236ce271c215"; :>> outcome = VerdictKind::pass; :>> judgedAgainst = "272821d"; :>> judgedAt = "2026-06-30"; :>> judgedBy = "ai"; }
        part storyLiveIndexDoDR4 : TestResult { :>> id = "8343db2f-af93-48a0-a64e-e4dc83dc44a0"; :>> outcome = VerdictKind::pass; :>> judgedAgainst = "bdd8f40"; :>> judgedAt = "2026-06-30"; :>> judgedBy = "ai"; }
        part storyLiveIndexDoDR5 : TestResult { :>> id = "20b97d41-6310-4baa-a6fb-8749fe0d3e1e"; :>> outcome = VerdictKind::pass; :>> judgedAgainst = "3b97ec1"; :>> judgedAt = "2026-07-02"; :>> judgedBy = "ai"; }
        part storyLiveIndexDoDR6 : TestResult { :>> id = "38e8235c-d0ee-441d-aa74-37a465427f77"; :>> outcome = VerdictKind::pass; :>> judgedAgainst = "4cd1b2a"; :>> judgedAt = "2026-07-02"; :>> judgedBy = "ai"; }
        part storyLiveIndexDoDR7 : TestResult { :>> id = "5217b8ea-8c49-48c9-bfe6-2ff9e5c10b09"; :>> outcome = VerdictKind::pass; :>> judgedAgainst = "cb32d15"; :>> judgedAt = "2026-07-02"; :>> judgedBy = "claudeOpus"; }
        part storyLiveIndexDoDR8 : TestResult { :>> id = "3d82a116-7df7-468b-a0ff-1b31e5842ebb"; :>> outcome = VerdictKind::pass; :>> judgedAgainst = "4a31e34"; :>> judgedAt = "2026-07-02"; :>> judgedBy = "claudeOpus"; }
        part storyLiveIndexDoDR9 : TestResult { :>> id = "a6252e75-0a49-4df3-86cb-9c75ce7d29df"; :>> outcome = VerdictKind::pass; :>> judgedAgainst = "6e90b2a"; :>> judgedAt = "2026-07-02"; :>> judgedBy = "claudeOpus"; }
        part storyLiveIndexDoDR10 : TestResult { :>> id = "e5096468-2276-44e5-9606-280e74055fe0"; :>> outcome = VerdictKind::pass; :>> judgedAgainst = "ceca03b"; :>> judgedAt = "2026-07-02"; :>> judgedBy = "claudeOpus"; }
        part storyLiveIndexDoDR11 : TestResult { :>> id = "4fb7d045-4315-49c3-acbd-c2a46d020195"; :>> outcome = VerdictKind::pass; :>> judgedAgainst = "da685ef"; :>> judgedAt = "2026-07-02"; :>> judgedBy = "claudeOpus"; }
        part storyLiveIndexDoDR12 : TestResult { :>> id = "7c376db7-edeb-4cb1-bfe8-dc59f1a6d14a"; :>> outcome = VerdictKind::pass; :>> judgedAgainst = "9f29e89"; :>> judgedAt = "2026-07-02"; :>> judgedBy = "claudeOpus"; }
    }

    verification liveIndexRefineGate : Test { :>> id = "7a1381c5-ff74-4eb6-ad76-2dbe79851508"; :>> title = "Sprint 5 refine gate (DoR)"; :>> createdAt = "2026-06-30"; :>> createdBy = "ai"; :>> method = VerificationMethod::inspect; :>> procedureText = "DoR: srLiveSync sliced into the index half (this) + the WS half (sprint06). Constraints from dCritiqueCorrectness (#1 continuous-watch+reconcile, #2 event-based invalidation) are explicit acceptance criteria. INVEST: Independent (builds on the existing VaultIndex; no unfinished dep); Valuable (the live-correct index, prerequisite to live sync); Estimable (8pts - notify + thread-safe incremental index + reconcile); Small (one sprint); Testable (FS-mutation + reconcile tests). DoR met."; }
    part liveIndexRefineGateR1 : TestResult { :>> id = "6860bb70-3166-4ea2-b314-be53155343f8"; :>> outcome = VerdictKind::pass; :>> judgedAgainst = "c68ed6a"; :>> judgedAt = "2026-06-30"; :>> judgedBy = "ai"; }
    verification liveIndexStandupGate : Test { :>> id = "71251be1-744e-4845-837b-0ea212dcb80f"; :>> title = "Sprint 5 standup gate"; :>> createdAt = "2026-06-30"; :>> createdBy = "ai"; :>> method = VerificationMethod::inspect; :>> procedureText = "Approach: make VaultIndex interior-mutable for lock-free reads (arc-swap ArcSwap<Tree>, or RwLock<Tree>); spawn a notify-debouncer-full watcher per vault at build time on a background thread; map debounced events to incremental tree mutations; reconcile (re-walk + diff) on watcher start. TDD each FS-mutation case with a tempdir + a bounded wait helper. No blockers; implement gate pends the build."; }
    part liveIndexStandupGateR1 : TestResult { :>> id = "a218488d-9681-4df2-b5b9-7c7a8cea196f"; :>> outcome = VerdictKind::pass; :>> judgedAgainst = "c68ed6a"; :>> judgedAt = "2026-06-30"; :>> judgedBy = "ai"; }
    verification liveIndexImplementGate : Test { :>> id = "36e21fd8-76da-480b-8951-28be942d8a4f"; :>> title = "Sprint 5 implement gate"; :>> createdAt = "2026-06-30"; :>> createdBy = "ai"; :>> method = VerificationMethod::test; :>> procedureText = "Built test-first (live_index_reflects_a_created_file watched RED via a skipped apply_paths, then GREEN). 17 tests pass: 6 live (create/modify/delete/rename/dir + reconcile_resyncs_after_a_missed_change) + app live-reflection regression + 10 prior. clippy -D warnings clean; fmt. Verified live at 882a80e."; }
    part liveIndexImplementGateR1 : TestResult { :>> id = "9b036c7f-c35f-4bb6-b1fe-3bd3b34c9d5c"; :>> outcome = VerdictKind::pass; :>> judgedAgainst = "882a80e"; :>> judgedAt = "2026-06-30"; :>> judgedBy = "ai"; }
    verification liveIndexReviewGate : Test { :>> id = "4d69a010-c490-4daf-a77e-7bc64d85488c"; :>> title = "Sprint 5 review gate"; :>> createdAt = "2026-06-30"; :>> createdBy = "ai"; :>> method = VerificationMethod::inspect; :>> procedureText = "Reviewed: ArcSwap gives lock-free reads (warm GET /api/fs/tree stays fast); watcher armed BEFORE the authoritative reconcile (no missed-event race) - the key fix over Ignis's WS-gated watcher; apply_paths is event-based + incremental (no dir-mtime, no full re-walk). dCritiqueCorrectness #1+#2 genuinely met (reconcile test proves no-silent-divergence). Two honest robustness gaps logged (issue006 watcher auto-restart, issue007 bulk-move subtree) - not blocking; reconcile() is the backstop. Sound."; }
    part liveIndexReviewGateR1 : TestResult { :>> id = "97ec550f-5b37-4cfb-9d9b-5179915fc473"; :>> outcome = VerdictKind::pass; :>> judgedAgainst = "882a80e"; :>> judgedAt = "2026-06-30"; :>> judgedBy = "ai"; }
    verification liveIndexCloseOutGate : Test { :>> id = "dee88952-e651-46f7-8c05-bf8dc181ed92"; :>> title = "Sprint 5 closeOut gate (autonomous, D0049)"; :>> createdAt = "2026-06-30"; :>> createdBy = "ai"; :>> method = VerificationMethod::inspect; :>> procedureText = "Autonomous closeOut (D0049): DoD pass; the index half of srLiveSync is built + correct under FS change. cargo test (17) + clippy + keel validate/guard green. WS delivery is sprint06."; }
    part liveIndexCloseOutGateR1 : TestResult { :>> id = "397bc0ac-7a3c-4663-bf1f-9a01196a0610"; :>> outcome = VerdictKind::pass; :>> judgedAgainst = "882a80e"; :>> judgedAt = "2026-06-30"; :>> judgedBy = "ai"; }
    verification liveIndexRetroGate : Test { :>> id = "884ac525-841a-4075-9613-6a39c42892ff"; :>> title = "Sprint 5 retro gate (autonomous, D0049)"; :>> createdAt = "2026-06-30"; :>> createdBy = "ai"; :>> method = VerificationMethod::analyze; :>> procedureText = "Autonomous retro (D0049). WELL: the dCritiqueCorrectness constraints, locked BEFORE the build, drove the design straight to the watch-before-reconcile ordering + event-based incremental updates - we avoided Ignis's two staleness bugs by construction, and the reconcile test proves no-silent-divergence. ArcSwap kept reads lock-free. AVOIDABLE-ISSUE SCAN -> tracked: issue006 (watcher death has no auto-restart - a dead watcher would silently re-introduce staleness, the very thing we fixed; Medium), issue007 (bulk-move populated dir under-populates until child events / reconcile; Low). LESSON: design constraints recorded ahead of code are cheap and steer the architecture; a live watcher's FAILURE path (not just its happy path) is itself a correctness surface. Estimate 8pt held."; }
    part liveIndexRetroGateR1 : TestResult { :>> id = "560e82f4-afd1-4c43-9752-73861530ec43"; :>> outcome = VerdictKind::pass; :>> judgedAgainst = "882a80e"; :>> judgedAt = "2026-06-30"; :>> judgedBy = "ai"; }
}
