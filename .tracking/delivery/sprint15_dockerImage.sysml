// IgniteDeliveryS15 — Sprint 15: the Docker image (dDeploymentDirection). Multi-stage build
// (Rust binary + Ignis browser JS + runtime Obsidian download) + compose + entrypoint. The
// AI-verifiable DoD is: image builds + in-container server smoke test. The full browser-loads-
// Obsidian check is a SEPARATE human demo (D0049). PLANNED to standup; implement gate pends build.
package IgniteDeliveryS15 {
    private import EngineElement::*;
    private import EngineWork::*;
    private import EngineVerification::*;
    private import EngineRelationships::*;

    // chartered by the deployment Decision it realizes (name-ref, no import).
    #CharteredBy dependency from dockerImageStory to dDeploymentDirection;

    part dockerImageStory : Story {
        :>> id = "7ebae27d-bdb0-4912-bfbf-51b2dde8626a";
        :>> title = "Sprint 15: Docker image - Rust binary + Ignis JS + runtime Obsidian download + compose (dDeploymentDirection)";
        :>> createdAt = "2026-07-02"; :>> createdBy = "will"; :>> kind = WorkKind::code; :>> priority = WorkPriority::p1; :>> owner = "ai"; :>> estimatedPoints = 5;
    }

    action def DeliveryRunS15 {
        action storyDockerImage;
        verification storyDockerImageDoD : Test { :>> id = "24370e1c-78d7-4aad-9448-b275266feaf5"; :>> method = VerificationMethod::test; :>> procedureText = "Ship Ignite as a Docker image per dDeploymentDirection. (1) A multi-stage Dockerfile at repo root: (a) rust:1 builds the ignite-server release binary; (b) a node stage clones Ignis@c9656b8 + builds its browser JS (packages/ui + shim); (c) a debian-slim runtime with the binary + built Ignis JS + an entrypoint that downloads the Obsidian bundle at runtime (mirroring Ignis's entrypoint) and execs ignite-server; env VAULT_ROOT=/vaults, OBSIDIAN_ASSETS_PATH, IGNITE_UI_DIST, IGNITE_SHIM_DIST, PORT=8080; VOLUME /vaults. (2) docker-compose.yml (vault bind-mount + port). AI-VERIFIABLE (method=test/inspect): `docker build` succeeds; `docker run` with a bind-mounted test vault -> GET /api/version, /api/vault/list, and /api/bootstrap respond correctly in-container. NOTE: the FULL end-to-end (a browser loads + operates Obsidian against the container) is a SEPARATE human demo verification (method=demo, D0049) - NOT self-attested here."; }
        part storyDockerImageDoDR1 : TestResult { :>> id = "3095cf24-e7d2-47e3-867d-a16a1265d67b"; :>> outcome = VerdictKind::pass; :>> judgedAgainst = "73ed632"; :>> judgedAt = "2026-07-02"; :>> judgedBy = "ai"; :>> notes = "Multi-stage Dockerfile builds (image 370MB). Smoke test FOUND + fixed a real bug: rust:1 (trixie) linked GLIBC_2.39 the node:22-slim (bookworm) runtime lacked -> binary wouldn't run; pinned rust:1-bookworm. Re-run: container READY ~8s; GET /api/version {build:dev,obsidianVersion:1.12.7,version:0.1.0}, /api/vault/list [{TestVault}], /api/bootstrap + /api/fs/tree return correct Ignis-shaped JSON for a bind-mounted vault; logs 'indexed 1 vault(s) ... listening on 0.0.0.0:8080'. Entrypoint downloaded Obsidian + installed obsidian-headless successfully. AI-verifiable DoD (build + in-container server smoke) MET. The browser-loads-Obsidian end-to-end is a separate human demo -> issue013."; }
        part storyDockerImageDoDR2 : TestResult { :>> id = "caaed0ff-ceff-47a9-b9f5-d57d53c892b2"; :>> outcome = VerdictKind::pass; :>> judgedAgainst = "9f29e89"; :>> judgedAt = "2026-07-02"; :>> judgedBy = "claudeOpus"; }
    }

    verification dockerImageRefineGate : Test { :>> id = "9b9092de-8f02-435e-b92c-5a8f30e8e855"; :>> title = "Sprint 15 refine gate (DoR)"; :>> createdAt = "2026-07-02"; :>> createdBy = "ai"; :>> method = VerificationMethod::inspect; :>> procedureText = "DoR: the Docker ship target (dDeploymentDirection - Docker only, reuse Ignis JS). Model mirrors Ignis's Docker entrypoint (runtime Obsidian download). Scope split: AI verifies build + server smoke; the browser-loads-Obsidian demo is a human gate. INVEST: Independent (packaging over the finished server); Valuable (runnable Ignite); Estimable (5pts - Dockerfile + compose + entrypoint); Small; Testable (docker build + in-container curl). DoR met."; }
    part dockerImageRefineGateR1 : TestResult { :>> id = "cb02707f-b000-4820-bdec-a54dbd9348a5"; :>> outcome = VerdictKind::pass; :>> judgedAgainst = "6cf33e2"; :>> judgedAt = "2026-07-02"; :>> judgedBy = "ai"; }
    verification dockerImageStandupGate : Test { :>> id = "761f881d-ac45-479d-a442-452cf76127d7"; :>> title = "Sprint 15 standup gate"; :>> createdAt = "2026-07-02"; :>> createdBy = "ai"; :>> method = VerificationMethod::inspect; :>> procedureText = "Approach: repo-root Dockerfile (rust:1 build stage -> ignite-server; node stage clones Ignis@c9656b8 + builds ui/shim; debian-slim runtime + entrypoint.sh that fetches the Obsidian bundle then execs the server); docker-compose.yml with a /vaults bind-mount + PORT. Verify with docker build + docker run + curl /api/version|vault/list|bootstrap against a test vault. Hand the browser-load demo to will. No blockers; implement gate pends the build + smoke."; }
    part dockerImageStandupGateR1 : TestResult { :>> id = "1967ece1-b0d7-46dc-b547-289f3cfed84e"; :>> outcome = VerdictKind::pass; :>> judgedAgainst = "6cf33e2"; :>> judgedAt = "2026-07-02"; :>> judgedBy = "ai"; }
    verification dockerImageImplementGate : Test { :>> id = "469e57b3-d403-429c-898b-8d8f24e75ed9"; :>> title = "Sprint 15 implement gate"; :>> createdAt = "2026-07-02"; :>> createdBy = "ai"; :>> method = VerificationMethod::test; :>> procedureText = "Dockerfile + entrypoint.sh + docker-compose(.stack).yml + Caddyfile written. docker build succeeds (370MB). Smoke test caught the GLIBC_2.39 mismatch (rust:1 trixie vs node:22-slim bookworm) -> fixed to rust:1-bookworm; re-run confirms the server runs in-container (version/vault-list/bootstrap/fs-tree correct, Obsidian downloaded + ob installed, listening). Verified live at 73ed632."; }
    part dockerImageImplementGateR1 : TestResult { :>> id = "1ddaf630-5957-4714-b345-01ecef05f49f"; :>> outcome = VerdictKind::pass; :>> judgedAgainst = "73ed632"; :>> judgedAt = "2026-07-02"; :>> judgedBy = "ai"; }
    verification dockerImageReviewGate : Test { :>> id = "26d1500f-4cef-4f48-974d-a1fd5b986967"; :>> title = "Sprint 15 review gate"; :>> createdAt = "2026-07-02"; :>> createdBy = "ai"; :>> method = VerificationMethod::inspect; :>> procedureText = "Reviewed: faithful adaptation of Ignis's entrypoint (runtime Obsidian download + ob install) execing the Rust binary; reuses Ignis's built ui/shim/template per dDeploymentDirection; base-image glibc lockstep documented; Caddy stack gives HTTPS + WS pass-through for remote use. Honest boundary: the browser-loads-Obsidian end-to-end is unverified (human demo, issue013) and the Ignis-asset wiring may need a tweak once browser-tested. Server-side deploy is sound + smoke-passed."; }
    part dockerImageReviewGateR1 : TestResult { :>> id = "9440528e-1270-4492-b571-e40045cda041"; :>> outcome = VerdictKind::pass; :>> judgedAgainst = "73ed632"; :>> judgedAt = "2026-07-02"; :>> judgedBy = "ai"; }
    verification dockerImageCloseOutGate : Test { :>> id = "d53b117c-c932-46d1-a16c-eeca22cfb076"; :>> title = "Sprint 15 closeOut gate (autonomous, D0049)"; :>> createdAt = "2026-07-02"; :>> createdBy = "ai"; :>> method = VerificationMethod::inspect; :>> procedureText = "Autonomous closeOut (D0049): AI-verifiable DoD pass (image builds + server smoke-responds in-container). Ignite is deployable as a Docker image; the full browser demo is the human gate (issue013). keel validate + guard green. This completes the major build; the remaining backlog is the tracked Low/Medium refinement issues."; }
    part dockerImageCloseOutGateR1 : TestResult { :>> id = "bb19bc0d-c60d-4c9d-aafd-e79a09adcf6e"; :>> outcome = VerdictKind::pass; :>> judgedAgainst = "73ed632"; :>> judgedAt = "2026-07-02"; :>> judgedBy = "ai"; }
    verification dockerImageRetroGate : Test { :>> id = "6a0d5157-0969-4cd9-a0b9-2718ac877229"; :>> title = "Sprint 15 retro gate (autonomous, D0049)"; :>> createdAt = "2026-07-02"; :>> createdBy = "ai"; :>> method = VerificationMethod::analyze; :>> procedureText = "Autonomous retro (D0049). WELL: the in-container SERVER smoke test earned its keep - it caught a glibc mismatch that a 'docker build succeeds' check would have missed entirely ('builds' != 'runs'); the fix (base-image lockstep) is a one-liner + a comment. Reusing Ignis's entrypoint verbatim (minus the exec target) de-risked the Obsidian download. AVOIDABLE-ISSUE SCAN -> issue013 (end-to-end browser load unverified; human demo + likely Ignis-asset-wiring iteration). LESSON: for a compiled artifact, always smoke-run it in the ACTUAL runtime image, and keep build/runtime base glibc in lockstep. Estimate 5pt held. Major build complete across 15 sprints."; }
    part dockerImageRetroGateR1 : TestResult { :>> id = "89577e60-d301-45da-8b73-f7b811c311a2"; :>> outcome = VerdictKind::pass; :>> judgedAgainst = "73ed632"; :>> judgedAt = "2026-07-02"; :>> judgedBy = "ai"; }
}
