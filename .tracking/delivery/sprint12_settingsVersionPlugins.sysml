// IgniteDeliveryS12 — Sprint 12: settings + version + plugins info endpoints (srWireCompat).
// Small config/info surface. Server-plugin listing is [] until native headless-sync (dPlugins).
// PLANNED to standup; implement gate pends the build.
package IgniteDeliveryS12 {
    private import EngineElement::*;
    private import EngineWork::*;
    private import EngineVerification::*;
    private import EngineRelationships::*;

    #CharteredBy dependency from settingsStory to srWireCompat;

    part settingsStory : Story {
        :>> id = "0837dfd6-f7b8-461c-842b-9e2abf88b307";
        :>> title = "Sprint 12: /api/settings (get/post) + /api/version + /api/plugins (srWireCompat)";
        :>> createdAt = "2026-07-02"; :>> createdBy = "will"; :>> kind = WorkKind::code; :>> priority = WorkPriority::p2; :>> owner = "ai"; :>> estimatedPoints = 5;
    }

    action def DeliveryRunS12 {
        action storySettings;
        verification storySettingsDoD : Test { :>> id = "86bb750a-f2db-4d5c-82d1-0cd2f22089ff"; :>> method = VerificationMethod::test; :>> procedureText = "Implement, wire-compatible with Ignis c9656b8 (check settings.js/version.js/plugins.js): GET /api/settings -> the effective settings object (defaults + env + persisted settings.json in DATA_ROOT) with Ignis's keys (proxyMode, proxyAllowlist, proxyAllowPrivate, contentCacheBytes, inputCacheBytes, inputCacheTtlMs, writeCoalesceMs, maxBodyBytes, directFetchHosts, wsOrigins); POST /api/settings (partial) -> validates (number ranges, proxy modes, list formats) + persists to settings.json + returns the updated effective settings. GET /api/version -> {version, build, obsidianVersion}. GET /api/plugins -> [] (no server plugins until native headless-sync, dPlugins); POST /api/plugins/:id/enable|disable -> 404 (no such plugin yet). NOTE: writeCoalesceMs is retained as a wire field but is a no-op (coalescing retired per dCritiqueCorrectness #3). VERIFY (axum oneshot): settings GET shape; POST persists + round-trips + rejects invalid; version shape; plugins -> []; enable unknown -> 404. clippy -D warnings + cargo test green; keel validate + guard green."; }
        part storySettingsDoDR1 : TestResult { :>> id = "b9f3be48-d28b-4dfd-a5ae-337b19758827"; :>> outcome = VerdictKind::pass; :>> judgedAgainst = "4a31e34"; :>> judgedAt = "2026-07-02"; :>> judgedBy = "ai"; :>> notes = "src/settings_routes.rs: Settings with Ignis DEFAULTS keys, effective=defaults<-env<-server-settings.json (DATA_ROOT), validated per settings.js + persisted; GET/POST /api/settings; GET /api/version {version,build,obsidianVersion}; GET /api/plugins->[]; enable/disable->error. State injected (Arc<RwLock<Settings>>). 69 tests pass (7 new), clippy + fmt clean. Caveats: writeCoalesceMs is a no-op wire field (dCritiqueCorrectness #3); POST /api/settings does NOT yet drive the proxy at runtime (proxy reads its own env ProxyConfig) -> issue010 (Low); a JSON float like 1234.0 is rejected where JS Number.isInteger accepts (clients send ints - negligible)."; }
        part storySettingsDoDR2 : TestResult { :>> id = "bdcdb2c4-31ec-4769-b8ff-ab7cc8ef83fe"; :>> outcome = VerdictKind::pass; :>> judgedAgainst = "ceca03b"; :>> judgedAt = "2026-07-02"; :>> judgedBy = "claudeOpus"; }
        part storySettingsDoDR3 : TestResult { :>> id = "287c1ea1-528b-4c47-8fb7-4612c28c726b"; :>> outcome = VerdictKind::pass; :>> judgedAgainst = "da685ef"; :>> judgedAt = "2026-07-02"; :>> judgedBy = "claudeOpus"; }
        part storySettingsDoDR4 : TestResult { :>> id = "c15de342-051c-4077-b45f-217f68fc9695"; :>> outcome = VerdictKind::pass; :>> judgedAgainst = "9f29e89"; :>> judgedAt = "2026-07-02"; :>> judgedBy = "claudeOpus"; }
    }

    verification settingsRefineGate : Test { :>> id = "f0804570-4f6d-4d06-bea6-4b672af3c9eb"; :>> title = "Sprint 12 refine gate (DoR)"; :>> createdAt = "2026-07-02"; :>> createdBy = "ai"; :>> method = VerificationMethod::inspect; :>> procedureText = "DoR: the config/info endpoints of srWireCompat. Shapes/validation from settings.js/version.js/plugins.js. INVEST: Independent (self-contained); Valuable (the client reads settings + version on load; plugins list); Estimable (5pts - 3 small route groups + settings persistence + validation); Small; Testable (oneshot). writeCoalesceMs kept as a no-op wire field (dCritiqueCorrectness #3). DoR met."; }
    part settingsRefineGateR1 : TestResult { :>> id = "b69e8220-e8f3-4efe-9966-a61facfdeb0c"; :>> outcome = VerdictKind::pass; :>> judgedAgainst = "d31a9ec"; :>> judgedAt = "2026-07-02"; :>> judgedBy = "ai"; }
    verification settingsStandupGate : Test { :>> id = "8d117b7c-1916-4b53-a2ab-2546449bad6c"; :>> title = "Sprint 12 standup gate"; :>> createdAt = "2026-07-02"; :>> createdBy = "ai"; :>> method = VerificationMethod::inspect; :>> procedureText = "Approach: a settings module (Settings struct with Ignis's keys + serde defaults; load = defaults<-env<-settings.json; POST validates + persists to DATA_ROOT/settings.json); version handler ({version=env CARGO_PKG_VERSION or IGNITE_VERSION, build, obsidianVersion=OBSIDIAN_VERSION}); plugins handler returns []; enable/disable -> 404. TDD each with oneshot + a tempdir DATA_ROOT. No blockers; implement gate pends the build."; }
    part settingsStandupGateR1 : TestResult { :>> id = "c8dd9be3-ac29-4151-a2c8-6b302b19149a"; :>> outcome = VerdictKind::pass; :>> judgedAgainst = "d31a9ec"; :>> judgedAt = "2026-07-02"; :>> judgedBy = "ai"; }
    verification settingsImplementGate : Test { :>> id = "3796927f-3dee-47e6-9979-69bdfc5a7f66"; :>> title = "Sprint 12 implement gate"; :>> createdAt = "2026-07-02"; :>> createdBy = "ai"; :>> method = VerificationMethod::test; :>> procedureText = "Built test-first (7 tests RED at not-implemented then GREEN). 69 tests pass: get-defaults, post-persists-round-trips, invalid-proxyMode-400, invalid-maxBody-400, version-shape, plugins-empty, plugin-enable-unknown. clippy -D warnings + fmt clean. Verified live at 4a31e34."; }
    part settingsImplementGateR1 : TestResult { :>> id = "696a0d7c-ff3d-4f0a-b311-7b476f1dc360"; :>> outcome = VerdictKind::pass; :>> judgedAgainst = "4a31e34"; :>> judgedAt = "2026-07-02"; :>> judgedBy = "ai"; }
    verification settingsReviewGate : Test { :>> id = "773e5d9c-47a5-4f77-9719-5537199f9cbb"; :>> title = "Sprint 12 review gate"; :>> createdAt = "2026-07-02"; :>> createdBy = "ai"; :>> method = VerificationMethod::inspect; :>> procedureText = "Reviewed: settings keys + DEFAULTS + validation match settings.js (quoted); file = server-settings.json in DATA_ROOT (matches Ignis); env-only keys excluded on write; state injected (no test env race). version/plugins shapes match. Accepted deferrals: writeCoalesceMs no-op (coalescing retired); POST->proxy runtime wiring deferred to issue010 (Low). Sound."; }
    part settingsReviewGateR1 : TestResult { :>> id = "9c36c4a9-dfbd-4d99-9575-8564a77a3f97"; :>> outcome = VerdictKind::pass; :>> judgedAgainst = "4a31e34"; :>> judgedAt = "2026-07-02"; :>> judgedBy = "ai"; }
    verification settingsCloseOutGate : Test { :>> id = "156177b7-00fa-4b42-8d6f-e6d79b4375b1"; :>> title = "Sprint 12 closeOut gate (autonomous, D0049)"; :>> createdAt = "2026-07-02"; :>> createdBy = "ai"; :>> method = VerificationMethod::inspect; :>> procedureText = "Autonomous closeOut (D0049): DoD pass; settings/version/plugins endpoints built. cargo test (69) + clippy + keel validate/guard green. Remaining srWireCompat: download/zip, native headless-sync (dPlugins) + deployment."; }
    part settingsCloseOutGateR1 : TestResult { :>> id = "70b114b5-1a52-4d9b-a8c5-6ed914018896"; :>> outcome = VerdictKind::pass; :>> judgedAgainst = "4a31e34"; :>> judgedAt = "2026-07-02"; :>> judgedBy = "ai"; }
    verification settingsRetroGate : Test { :>> id = "a4a19758-0960-4420-89ca-9e1ce8fdc313"; :>> title = "Sprint 12 retro gate (autonomous, D0049)"; :>> createdAt = "2026-07-02"; :>> createdBy = "ai"; :>> method = VerificationMethod::analyze; :>> procedureText = "Autonomous retro (D0049). WELL: small config sprint landed cleanly by matching settings.js DEFAULTS + validation verbatim; state injection kept tests hermetic (tempdir DATA_ROOT). AVOIDABLE-ISSUE SCAN -> issue010 (POST /api/settings doesn't drive the proxy at runtime yet - proxy reads env at startup; Low). Ignis's writeCoalescer.configure + bootstrap.invalidateAll POST side-effects have no analog (coalescing retired; live index makes invalidation moot). LESSON: retiring a subsystem (coalescing) still means keeping its wire FIELD for compat while making it a documented no-op. Estimate 5pt held."; }
    part settingsRetroGateR1 : TestResult { :>> id = "53a12620-0166-49c4-adc4-c9c14e303a93"; :>> outcome = VerdictKind::pass; :>> judgedAgainst = "4a31e34"; :>> judgedAt = "2026-07-02"; :>> judgedBy = "ai"; }
}
