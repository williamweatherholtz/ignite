// IgniteDeliveryS03 — Sprint 3: honest end-to-end Ignite-vs-Ignis benchmark in Docker's
// bind-mount context (resolves issue004). Covers the dockerContextBench backlog action.
// IN PROGRESS: refine + standup passed; the Dockerfile + harness are authored, but the
// implement gate is PENDING until Docker Desktop is running and the measurement is taken
// (D0051 - no fabricated evidence; the implement gate's evidence is the real in-Docker run).
package IgniteDeliveryS03 {
    private import EngineElement::*;
    private import EngineWork::*;
    private import EngineVerification::*;
    private import EngineRelationships::*;

    // dockerContextBench (IgniteBacklog) referenced by name in the #CharteredBy edge (no import).
    #CharteredBy dependency from dockerContextBenchStory to dockerContextBench;

    part dockerContextBenchStory : Story {
        :>> id = "f9a8d054-bd97-436d-8cee-fda46d09eb33";
        :>> title = "Sprint 3: benchmark Ignite in Docker's bind-mount context for an honest end-to-end Ignis comparison (resolves issue004)";
        :>> createdAt = "2026-06-30"; :>> createdBy = "will"; :>> kind = WorkKind::research; :>> priority = WorkPriority::p1; :>> owner = "ai"; :>> estimatedPoints = 2;
    }

    action def DeliveryRunS03 {
        action storyDockerContextBench;
        verification storyDockerContextBenchDoD : Test { :>> id = "7376ce21-16fe-4110-8335-75d0e68a5e72"; :>> method = VerificationMethod::test; :>> procedureText = "Fill the Docker row of the 2x2 matrix {Ignite parallel-Rust, Ignis-algorithm sequential-Node} x {native, Docker}. Build the Ignite image (binary on container FS), run ignite-bench against the Games vault bind-mounted at /vault (same mechanism Ignis uses), and run the Node Ignis-algorithm baseline in a node container on the same mount. Record both Docker numbers; compare to the recorded native numbers (Ignite ~20ms; Node 657/216ms). VERIFY: state the TRUE end-to-end Ignis-vs-Ignite factor in the user's actual deployment context, and attribute the original 72-214s between Docker-FS overhead vs algorithm."; }
        part storyDockerContextBenchDoDR1 : TestResult { :>> id = "148f8211-6ebf-4f2b-a06e-48ce449723c1"; :>> outcome = VerdictKind::pass; :>> judgedAgainst = "8fc3505"; :>> judgedAt = "2026-06-30"; :>> judgedBy = "ai"; :>> notes = "Matrix filled (full numbers on dockerContextBenchDoDR1). Ignite-Docker 2.74s cold / 2.3ms warm; Node-Ignis-algo-Docker 27.15s cold. Honest end-to-end: Docker bind-mount dominates; Ignite ~10x faster than Ignis's algorithm in Docker; structural win = build-once-at-startup then ~2ms/request vs Ignis re-walking every request. Cold-miss-in-Docker -> issue005."; }
    }

    verification dockerContextBenchRefineGate : Test { :>> id = "6e236ba2-8c16-4087-8b3a-cbcea5d8bcf7"; :>> title = "Sprint 3 refine gate (DoR)"; :>> createdAt = "2026-06-30"; :>> createdBy = "ai"; :>> method = VerificationMethod::inspect; :>> procedureText = "DoR: issue004 needs an apples-to-apples Docker-context measurement. Approach is clear (multi-stage Dockerfile: binary on fast FS, only vault bind-mounted; node container for the Ignis-algorithm baseline). Vault path known (Downloads/Games). Blocked only on Docker Desktop running (a runtime precondition, not a design gap). DoR met."; }
    part dockerContextBenchRefineGateR1 : TestResult { :>> id = "89783367-1f37-44d4-97ba-72b2e2230e53"; :>> outcome = VerdictKind::pass; :>> judgedAgainst = "be574c4"; :>> judgedAt = "2026-06-30"; :>> judgedBy = "ai"; }
    verification dockerContextBenchStandupGate : Test { :>> id = "c484f302-ff9c-43b0-8994-d163c5a8023b"; :>> title = "Sprint 3 standup gate"; :>> createdAt = "2026-06-30"; :>> createdBy = "ai"; :>> method = VerificationMethod::inspect; :>> procedureText = "Approach implemented and committed: server/Dockerfile (multi-stage, binary on container FS, only /vault bind-mounted), server/bench/ignis-walk-baseline.js (in-Docker Node baseline), server/bench/run-docker-bench.ps1 (runs both, prints both). Precondition: user starts Docker Desktop, then `pwsh server/bench/run-docker-bench.ps1 <vault>`. No design blockers; implement gate pends the live run."; }
    part dockerContextBenchStandupGateR1 : TestResult { :>> id = "6c843e32-77b6-4102-89d1-b696c00e7db7"; :>> outcome = VerdictKind::pass; :>> judgedAgainst = "be574c4"; :>> judgedAt = "2026-06-30"; :>> judgedBy = "ai"; }
    verification dockerContextBenchImplementGate : Test { :>> id = "8050bf4a-3e2b-495b-94c5-0d0386bed5f1"; :>> title = "Sprint 3 implement gate"; :>> createdAt = "2026-06-30"; :>> createdBy = "ai"; :>> method = VerificationMethod::test; :>> procedureText = "Built the Ignite image (rust:1 multi-stage) + ran both benchmarks in Docker against the bind-mounted Games vault (2,972 entries). Ignite-Docker: cold 2.74s, warm 2.3ms. Node-Ignis-algorithm-Docker: 27.15s cold. Numbers recorded on dockerContextBenchDoDR1. Exit 0."; }
    part dockerContextBenchImplementGateR1 : TestResult { :>> id = "910d56a0-1b20-4728-9d60-cb97b6dca7de"; :>> outcome = VerdictKind::pass; :>> judgedAgainst = "8fc3505"; :>> judgedAt = "2026-06-30"; :>> judgedBy = "ai"; }
    verification dockerContextBenchReviewGate : Test { :>> id = "35498061-fd98-4a03-bbc9-d4567baf1ea1"; :>> title = "Sprint 3 review gate"; :>> createdAt = "2026-06-30"; :>> createdBy = "ai"; :>> method = VerificationMethod::inspect; :>> procedureText = "Reviewed: the 2x2 matrix is complete + honest. Docker bind-mount is the dominant raw cost (137x Ignite / 41x Node cold); Ignite still ~10x faster than Ignis's algorithm in Docker + warm-serves at 2.3ms; the real end-to-end story is the build-once-at-startup vs re-walk-every-request structural win. The Docker cold-miss is honestly logged as issue005, not buried. No overclaim remains."; }
    part dockerContextBenchReviewGateR1 : TestResult { :>> id = "f0e635d1-b379-47cb-bca2-0512684fe06c"; :>> outcome = VerdictKind::pass; :>> judgedAgainst = "8fc3505"; :>> judgedAt = "2026-06-30"; :>> judgedBy = "ai"; }
    verification dockerContextBenchCloseOutGate : Test { :>> id = "c2197137-cdf9-4878-a743-688d3aa920ef"; :>> title = "Sprint 3 closeOut gate (autonomous, D0049)"; :>> createdAt = "2026-06-30"; :>> createdBy = "ai"; :>> method = VerificationMethod::inspect; :>> procedureText = "Autonomous closeOut (D0049): DoD pass; issue004 resolved (honest end-to-end Docker-context comparison done + recorded). issue005 spun off for the Docker cold-build miss. keel validate + guard green."; }
    part dockerContextBenchCloseOutGateR1 : TestResult { :>> id = "5e370489-5d01-464b-a146-14515df37d1c"; :>> outcome = VerdictKind::pass; :>> judgedAgainst = "8fc3505"; :>> judgedAt = "2026-06-30"; :>> judgedBy = "ai"; }
    verification dockerContextBenchRetroGate : Test { :>> id = "62eeaffd-9120-40b5-acf7-d6acc2cf5bec"; :>> title = "Sprint 3 retro gate (autonomous, D0049)"; :>> createdAt = "2026-06-30"; :>> createdBy = "ai"; :>> method = VerificationMethod::analyze; :>> procedureText = "Autonomous retro (D0049). WELL: pushing the comparison into Ignis's ACTUAL Docker context turned a confounded headline into a defensible end-to-end story - per-request tree load drops from tens of seconds (Ignis, every request) to ~2ms (Ignite, warm after a one-time startup), with Docker's bind mount as the dominant raw cost. AVOIDABLE-ISSUE SCAN -> issue005 (Docker cold mitigation + deployment guidance). LESSON: the warm-index architecture's value is LARGEST exactly where the filesystem is slow (Docker) - it amortizes one cold walk across all requests, which is the structural advantage over Ignis's per-request re-walk. Estimate 2pt held."; }
    part dockerContextBenchRetroGateR1 : TestResult { :>> id = "cf6ae332-5295-442a-9866-183115868bf7"; :>> outcome = VerdictKind::pass; :>> judgedAgainst = "8fc3505"; :>> judgedAt = "2026-06-30"; :>> judgedBy = "ai"; }
}
