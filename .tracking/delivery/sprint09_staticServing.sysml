// IgniteDeliveryS09 — Sprint 9: static + app-shell serving (srWireCompat). ServeDir for
// assets/ui/shim/obsidian, GET / index.html script-tag injection, /vault-files/<vault>/<path>
// serving, ?v= cache headers. The injection + serving LOGIC (fixture-tested); the real
// Obsidian bundle + built Ignis JS are deploy-time assets (a later deployment task).
// PLANNED to standup; implement gate pends the build.
package IgniteDeliveryS09 {
    private import EngineElement::*;
    private import EngineWork::*;
    private import EngineVerification::*;
    private import EngineRelationships::*;

    // chartered by srWireCompat (IgniteRequirements); name-ref, no import.
    #CharteredBy dependency from staticServingStory to srWireCompat;

    part staticServingStory : Story {
        :>> id = "09fcceb1-7f64-435f-9d59-5d566ebe98a2";
        :>> title = "Sprint 9: static + app-shell serving - index.html injection + /vault-files + ServeDir (srWireCompat)";
        :>> createdAt = "2026-07-02"; :>> createdBy = "will"; :>> kind = WorkKind::code; :>> priority = WorkPriority::p1; :>> owner = "ai"; :>> estimatedPoints = 8;
    }

    action def DeliveryRunS09 {
        action storyStaticServing;
        verification storyStaticServingDoD : Test { :>> id = "9b140ffa-a8ae-4c6b-9c3e-9f43947fb796"; :>> method = VerificationMethod::test; :>> procedureText = "Serve the app shell wire-compatible with Ignis c9656b8 (check index.js:124-174 in the cloned source for the exact injection): (1) GET / (and /index.html) returns HTML built by discovering Obsidian's <script src> tags from the Obsidian bundle's index.html, version-stamping them, and injecting them + the Ignis shim-loader/ui scripts into the ignis template; (2) static file serving (tower-http ServeDir) for the assets dir, the built ui/shim dist, and the Obsidian assets dir (paths from env: OBSIDIAN_ASSETS_PATH etc.); (3) GET /vault-files/<vaultId>/<relpath> serves vault files (images/attachments) with WITHIN-VAULT path security (reuse the traversal guard); (4) ?v=<version> cache-control headers. VERIFY (fixture tests): given a fake Obsidian index.html (with script tags) + a template, GET / produces HTML containing the injected + version-stamped scripts; a static asset is served from a fixture dir; /vault-files serves a file from a tempdir vault and REJECTS traversal; unknown paths 404. clippy -D warnings + cargo test green; keel validate + guard green. (Acquiring the REAL Obsidian bundle + building Ignis's JS = a deploy-time task, not this sprint.)"; }
        part storyStaticServingDoDR1 : TestResult { :>> id = "cf84a83b-e4a5-42a7-bae3-f35fb89aef4a"; :>> outcome = VerdictKind::pass; :>> judgedAgainst = "3b97ec1"; :>> judgedAt = "2026-07-02"; :>> judgedBy = "ai"; :>> notes = "src/static_routes.rs: build_index_html replicates Ignis index.js:124-174 (same scriptRegex + placeholders + version-stamping); cache_control_for mirrors cache-headers.js; /vault-files reuses resolve_in_vault (traversal rejected); ServeDir for assets/ui/shim/obsidian with API routes winning. 49 tests pass (8 new incl. injection + vault-files-traversal + cache-header), clippy + fmt clean. Deploy-time assets (real ignis template + built ui/shim JS + Obsidian bundle) used as fixtures in tests, not fabricated."; }
        part storyStaticServingDoDR2 : TestResult { :>> id = "be79e018-9404-4a0b-9162-f1b110b935d6"; :>> outcome = VerdictKind::pass; :>> judgedAgainst = "cb32d15"; :>> judgedAt = "2026-07-02"; :>> judgedBy = "claudeOpus"; }
        part storyStaticServingDoDR3 : TestResult { :>> id = "1646ef72-8d6d-490f-83f8-9ea03934dd89"; :>> outcome = VerdictKind::pass; :>> judgedAgainst = "4a31e34"; :>> judgedAt = "2026-07-02"; :>> judgedBy = "claudeOpus"; }
        part storyStaticServingDoDR4 : TestResult { :>> id = "7ee97cd1-19bf-4077-a9c5-1fe4202a1585"; :>> outcome = VerdictKind::pass; :>> judgedAgainst = "6e90b2a"; :>> judgedAt = "2026-07-02"; :>> judgedBy = "claudeOpus"; }
        part storyStaticServingDoDR5 : TestResult { :>> id = "2a2fd9f2-39a7-48ab-8a7c-6d33f10ee737"; :>> outcome = VerdictKind::pass; :>> judgedAgainst = "ceca03b"; :>> judgedAt = "2026-07-02"; :>> judgedBy = "claudeOpus"; }
        part storyStaticServingDoDR6 : TestResult { :>> id = "94de45cf-5a46-4d89-a134-07c9ea0363c4"; :>> outcome = VerdictKind::pass; :>> judgedAgainst = "da685ef"; :>> judgedAt = "2026-07-02"; :>> judgedBy = "claudeOpus"; }
        part storyStaticServingDoDR7 : TestResult { :>> id = "2dc00a70-0cd7-41b9-85db-e33690445582"; :>> outcome = VerdictKind::pass; :>> judgedAgainst = "9f29e89"; :>> judgedAt = "2026-07-02"; :>> judgedBy = "claudeOpus"; }
    }

    verification staticServingRefineGate : Test { :>> id = "8f23e33d-a356-4390-aaf3-1666f91a43e9"; :>> title = "Sprint 9 refine gate (DoR)"; :>> createdAt = "2026-07-02"; :>> createdBy = "ai"; :>> method = VerificationMethod::inspect; :>> procedureText = "DoR: the app-shell serving surface of srWireCompat. Injection + serving behavior known from Ignis index.js/cache-headers.js. Scoped to the LOGIC (fixture-tested); real-bundle acquisition is deployment. INVEST: Independent (adds serving routes; reuses the fs path guard); Valuable (the shell that, with a real bundle at deploy, makes Obsidian load in a browser); Estimable (8pts - ServeDir + injection + vault-files + cache headers); Small-ish; Testable (fixtures). DoR met."; }
    part staticServingRefineGateR1 : TestResult { :>> id = "67cb84b5-ab2b-42ba-891b-09c9b7a35058"; :>> outcome = VerdictKind::pass; :>> judgedAgainst = "1ed1b11"; :>> judgedAt = "2026-07-02"; :>> judgedBy = "ai"; }
    verification staticServingStandupGate : Test { :>> id = "7862dad8-4bfc-496c-a5f7-8c1fcf958a44"; :>> title = "Sprint 9 standup gate"; :>> createdAt = "2026-07-02"; :>> createdBy = "ai"; :>> method = VerificationMethod::inspect; :>> procedureText = "Approach: a static/shell module: read the injection logic from Ignis index.js (discover <script src> in Obsidian's index.html, version-stamp, inject into the ignis template - all path-configurable via env with test fixtures); tower-http ServeDir for assets/ui/obsidian; a /vault-files/:vault/*path handler reusing resolve_in_vault; cache-control by ?v=. TDD injection + vault-files + a served asset against fixtures. No blockers; implement gate pends the build."; }
    part staticServingStandupGateR1 : TestResult { :>> id = "8dcbc4d3-69e6-454c-8ef5-203ba44373b9"; :>> outcome = VerdictKind::pass; :>> judgedAgainst = "1ed1b11"; :>> judgedAt = "2026-07-02"; :>> judgedBy = "ai"; }
    verification staticServingImplementGate : Test { :>> id = "0a6b2fd5-1adc-4f3c-a393-f24a12e077ec"; :>> title = "Sprint 9 implement gate"; :>> createdAt = "2026-07-02"; :>> createdBy = "ai"; :>> method = VerificationMethod::test; :>> procedureText = "Built test-first (build_index_html watched RED at todo!()). 49 tests pass (3 static unit + 5 app integration + 41 prior): injection, version-omitted-when-unknown, /vault-files served+traversal-rejected+404, cache-header present/absent, API routes still win. clippy -D warnings + fmt clean. Verified live at 3b97ec1."; }
    part staticServingImplementGateR1 : TestResult { :>> id = "9c501757-c079-4ddb-bcb8-f6a32489a9e1"; :>> outcome = VerdictKind::pass; :>> judgedAgainst = "3b97ec1"; :>> judgedAt = "2026-07-02"; :>> judgedBy = "ai"; }
    verification staticServingReviewGate : Test { :>> id = "a370c881-c425-4a5d-98f4-9b74bbe1d13f"; :>> title = "Sprint 9 review gate"; :>> createdAt = "2026-07-02"; :>> createdBy = "ai"; :>> method = VerificationMethod::inspect; :>> procedureText = "Reviewed: injection matches Ignis index.js (same regex + placeholders quoted); cache_control_for matches cache-headers.js (asset-ext -> immutable, else 5m, middleware only fills when absent so /'s no-cache is preserved); /vault-files reuses the audited traversal guard; route ordering keeps the API winning over the static fallback (tested). Deploy-time assets honestly deferred (fixtures, not fabricated template). Sound."; }
    part staticServingReviewGateR1 : TestResult { :>> id = "565e4709-8179-47f2-8a1e-30a1541731d3"; :>> outcome = VerdictKind::pass; :>> judgedAgainst = "3b97ec1"; :>> judgedAt = "2026-07-02"; :>> judgedBy = "ai"; }
    verification staticServingCloseOutGate : Test { :>> id = "69cea3c1-9b7b-4258-9ac0-05300e31bdb5"; :>> title = "Sprint 9 closeOut gate (autonomous, D0049)"; :>> createdAt = "2026-07-02"; :>> createdBy = "ai"; :>> method = VerificationMethod::inspect; :>> procedureText = "Autonomous closeOut (D0049): DoD pass; the app-shell serving logic is built (index injection + static + /vault-files + cache). With deploy-time assets wired, a browser can load Obsidian against Ignite. cargo test (49) + clippy + keel validate/guard green. Remaining srWireCompat: vault create/rename/remove, proxy, settings/version/plugins, download/zip, native headless-sync + the deployment (Dockerfile/bundle)."; }
    part staticServingCloseOutGateR1 : TestResult { :>> id = "952af794-08cd-467f-943b-e7635be79d4e"; :>> outcome = VerdictKind::pass; :>> judgedAgainst = "3b97ec1"; :>> judgedAt = "2026-07-02"; :>> judgedBy = "ai"; }
    verification staticServingRetroGate : Test { :>> id = "bf65b82a-7d48-4890-9890-26ec3ab9488b"; :>> title = "Sprint 9 retro gate (autonomous, D0049)"; :>> createdAt = "2026-07-02"; :>> createdBy = "ai"; :>> method = VerificationMethod::analyze; :>> procedureText = "Autonomous retro (D0049). WELL: reading Ignis's index.js/cache-headers.js gave an exact injection + cache replica (regex + placeholders + ext table matched); reusing resolve_in_vault kept /vault-files security consistent with the fs routes. AVOIDABLE-ISSUE SCAN: no new tracked issues - the real template/JS/Obsidian bundle are honestly deferred as deploy-time assets (fixtures used, nothing fabricated); the shared-app.rs re-verify churn is a known friction (reverify.toml now targets server/ for batch re-verify). LESSON: for a closed-upstream shell, matching the reference's exact regex/placeholders beats re-inventing the template. Estimate 8pt held."; }
    part staticServingRetroGateR1 : TestResult { :>> id = "1d4d4042-23b3-49a0-91f8-bc2df761a387"; :>> outcome = VerdictKind::pass; :>> judgedAgainst = "3b97ec1"; :>> judgedAt = "2026-07-02"; :>> judgedBy = "ai"; }
}
